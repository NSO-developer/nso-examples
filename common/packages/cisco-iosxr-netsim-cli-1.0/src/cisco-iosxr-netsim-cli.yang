module cisco-iosxr-netsim-cli {
  yang-version 1.1;
  namespace "http://tail-f.com/ns/ned-id/cisco-iosxr-netsim-cli";
  prefix cisco-iosxr-netsim-cli;

  import tailf-common {
    prefix tailf;
  }

  import tailf-ncs-ned {
    prefix ned;
  }

  identity cisco-iosxr-netsim-cli {
    tailf:abstract;
    base ned:cli-ned-id;
  }
}
