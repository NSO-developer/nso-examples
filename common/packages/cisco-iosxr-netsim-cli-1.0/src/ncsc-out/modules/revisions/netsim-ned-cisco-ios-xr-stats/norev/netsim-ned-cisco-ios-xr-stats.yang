module netsim-ned-cisco-ios-xr-stats {
  // Generated by yanger -t ncs
  tailf:mount-id "cisco-iosxr-netsim-cli-1.0:cisco-iosxr-netsim-cli-1.0";
  tailf:ncs-device-type "cli-ned";

  namespace "http://tail-f.com/ned/cisco-ios-xr-stats";
  prefix cisco-ios-xr-stats;

  import tailf-common {
    prefix tailf;
  }
  import tailf-ncs {
    prefix ncs;
  }

  augment "/ncs:devices/ncs:device/ncs:config" {
    // NCS drop config false list inventory
    // NCS drop config false container cdp
    // NCS drop config false container lldp
    // NCS drop config false container controllers
    container exec {
      tailf:ncs-device-type "cli-ned";
      tailf:display-when "not(../../ncs:module) or ../../ncs:module[ncs:name='netsim-ned-cisco-ios-xr-stats']";
      tailf:alt-name "exec-stats";
    }
  }
  augment "/ncs:devices/ncs:device/ncs:live-status" {
    list inventory {
      tailf:ncs-device-type "cli-ned";
      tailf:display-when "not(../ncs:module) or ../ncs:module[ncs:name='netsim-ned-cisco-ios-xr-stats'] or (../ncs:live-status-protocol[not(ncs:capability)]) or (../ncs:live-status-protocol/ncs:capability/ncs:module[.='netsim-ned-cisco-ios-xr-stats'])";
      key "name";
      leaf name {
        type string;
      }
      leaf descr {
        type string;
      }
      leaf pid {
        type string;
      }
      leaf vid {
        type string;
      }
      leaf sn {
        type string;
      }
      tailf:alt-name "inventory-stats";
    }
    container cdp {
      tailf:ncs-device-type "cli-ned";
      tailf:display-when "not(../../ncs:module) or ../../ncs:module[ncs:name='netsim-ned-cisco-ios-xr-stats'] or (../../ncs:live-status-protocol[not(ncs:capability)]) or (../../ncs:live-status-protocol/ncs:capability/ncs:module[.='netsim-ned-cisco-ios-xr-stats'])";
      list neighbors {
        key "local-interface";
        leaf local-interface {
          type string;
        }
        leaf device-id {
          type string;
        }
        leaf hold-time {
          type string;
        }
        leaf capability {
          type string;
        }
        leaf platform {
          type string;
        }
        leaf port-id {
          type string;
        }
      }
      tailf:alt-name "cdp-stats";
    }
    container lldp {
      tailf:ncs-device-type "cli-ned";
      tailf:display-when "not(../../ncs:module) or ../../ncs:module[ncs:name='netsim-ned-cisco-ios-xr-stats'] or (../../ncs:live-status-protocol[not(ncs:capability)]) or (../../ncs:live-status-protocol/ncs:capability/ncs:module[.='netsim-ned-cisco-ios-xr-stats'])";
      list neighbors {
        key "local-interface";
        leaf local-interface {
          type string;
        }
        leaf parent-interface {
          type string;
        }
        leaf device-id {
          type string;
        }
        leaf time-remaining {
          type string;
        }
        leaf hold-time {
          type string;
        }
        leaf capability {
          type string;
        }
        leaf chassis-id {
          type string;
        }
        leaf port-id {
          type string;
        }
      }
      tailf:alt-name "lldp-stats";
    }
    container controllers {
      tailf:ncs-device-type "cli-ned";
      tailf:display-when "not(../../ncs:module) or ../../ncs:module[ncs:name='netsim-ned-cisco-ios-xr-stats'] or (../../ncs:live-status-protocol[not(ncs:capability)]) or (../../ncs:live-status-protocol/ncs:capability/ncs:module[.='netsim-ned-cisco-ios-xr-stats'])";
      list Optics {
        key "id";
        leaf id {
          type string;
        }
        container instance {
          // NCS drop tailf:cli-drop-node-name
          presence "true";
          leaf controller-state {
            type string;
          }
          container transceiver-vendor-details {
            leaf form-factor {
              type string;
            }
            leaf optics-type {
              type string;
            }
            leaf name {
              type string;
            }
            leaf oui-number {
              type string;
            }
            leaf part-number {
              type string;
            }
            leaf rev-number {
              type string;
            }
            leaf serial-number {
              type string;
            }
            leaf pid {
              type string;
            }
            leaf vid {
              type string;
            }
            leaf date-code {
              type string;
            }
          }
        }
      }
      tailf:alt-name "controllers-stats";
    }
    container exec {
      tailf:ncs-device-type "cli-ned";
      tailf:display-when "not(../../ncs:module) or ../../ncs:module[ncs:name='netsim-ned-cisco-ios-xr-stats'] or (../../ncs:live-status-protocol[not(ncs:capability)]) or (../../ncs:live-status-protocol/ncs:capability/ncs:module[.='netsim-ned-cisco-ios-xr-stats'])";
      tailf:alt-name "exec-stats";
    }
  }
}
