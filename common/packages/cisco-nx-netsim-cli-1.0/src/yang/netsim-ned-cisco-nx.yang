module netsim-ned-cisco-nx {
  namespace "http://tail-f.com/ned/cisco-nx";
  prefix nx;

  import tailf-common {
    prefix tailf;
  }
  import ietf-inet-types {
    prefix inet;
  }

  revision 2026-03-19;

  typedef ip-mask {
    type string;
  }

  typedef mac-address-type {
    type union {
      type string;
      type string;
      type string;
      type string;
    }
  }

  typedef vlan-list-type {
    type uint16;
  }

  typedef vlan-list-type-all {
    type union {
      type uint16;
      type enumeration {
        enum "all";
      }
    }
  }

  typedef vrf-member-type {
    type union {
      type enumeration {
        enum "default";
        enum "management";
      }
      type string;
    }
  }

  typedef dscp-type {
    type uint16;
  }

  typedef dscp-value-type {
    type union {
      type uint8;
      type enumeration {
        enum "af11";
        enum "af12";
        enum "af13";
        enum "af21";
        enum "af22";
        enum "af23";
        enum "af31";
        enum "af32";
        enum "af33";
        enum "af41";
        enum "af42";
        enum "af43";
        enum "cs1";
        enum "cs2";
        enum "cs3";
        enum "cs4";
        enum "cs5";
        enum "cs6";
        enum "cs7";
        enum "default";
        enum "ef";
      }
    }
  }

  typedef precedence-type {
    type enumeration {
      enum "critical";
      enum "flash";
      enum "flash-override";
      enum "immediate";
      enum "internet";
      enum "network";
      enum "priority";
      enum "routine";
    }
  }

  typedef class-name-type {
    type union {
      type enumeration {
        enum "class-default";
      }
      type string;
    }
  }

  typedef default-access-list-standard-id-type {
    type union {
      type uint8;
      type uint16;
    }
  }

  typedef access-list-standard-id-type {
    type union {
      type default-access-list-standard-id-type;
      type string;
    }
  }

  typedef ospf-area-type {
    type union {
      type uint32;
      type inet:ipv4-address;
    }
  }

  typedef enable-type {
    type enumeration {
      enum "enable";
    }
  }

  typedef protocol-port-type {
    type union {
      type uint16;
      type enumeration {
        enum "cmd" {
          value 514;
        }
        enum "ftp-data" {
          value 20;
        }
        enum "ftp" {
          value 21;
        }
        enum "telnet";
        enum "tacacs" {
          value 49;
        }
        enum "bootps" {
          value 67;
        }
        enum "bootpc" {
          value 68;
        }
        enum "tftp" {
          value 69;
        }
        enum "ntp" {
          value 123;
        }
        enum "snmp" {
          value 161;
        }
        enum "snmptrap" {
          value 162;
        }
        enum "bgp" {
          value 179;
        }
        enum "pim-auto-rp" {
          value 496;
        }
        enum "rip" {
          value 520;
        }
        enum "smtp";
        enum "domain";
        enum "syslog";
        enum "netbios-ns";
        enum "netbios-dgm";
        enum "netbios-ss";
        enum "time";
        enum "talk";
        enum "biff";
        enum "dnsix";
        enum "xdmcp";
        enum "who";
        enum "sunrpc";
        enum "nameserver";
        enum "mobile-ip";
        enum "isakmp";
        enum "chargen";
        enum "daytime";
        enum "discard";
        enum "drip";
        enum "echo";
        enum "exec";
        enum "finger";
        enum "ident";
        enum "non500-isakmp";
        enum "hostname";
        enum "irc";
        enum "pop2";
        enum "pop3";
        enum "klogin";
        enum "kshell";
        enum "login";
        enum "lpd";
        enum "uucp";
        enum "nntp";
        enum "whois";
        enum "www";
        enum "ssh";
      }
    }
  }

  typedef word32 {
    type string;
  }

  typedef word50 {
    type string;
  }

  typedef asn-ip-type {
    type string;
  }

  typedef policy-map-name-type {
    type string;
  }

  typedef asn-type {
    type union {
      type uint32;
      type string;
    }
  }

  typedef module-type {
    type enumeration {
      enum "f1";
      enum "f2";
      enum "f2e";
      enum "f3";
      enum "m1";
      enum "m1xl";
      enum "m2xl";
      enum "m3";
    }
  }

  typedef ospf-id-type {
    type union {
      type uint16;
      type string;
    }
  }

  typedef loglevel-type {
    type uint8;
  }

  typedef tcam-size-type {
    type uint32;
  }

  typedef xfer-speed-type {
    type enumeration {
      enum "bps";
      enum "kbps";
      enum "mbps";
      enum "gbps";
      enum "pps";
    }
  }

  typedef burst-type {
    type enumeration {
      enum "bytes";
      enum "kbytes";
      enum "mbytes";
      enum "ms";
      enum "us";
      enum "packets";
    }
  }

  typedef comparison-type {
    type enumeration {
      enum "eq";
      enum "ge";
      enum "gt";
      enum "le";
      enum "lt";
      enum "ne";
    }
  }

  typedef user-role-type {
    type union {
      type enumeration {
        enum "network-admin";
        enum "network-operator";
        enum "priv-0";
        enum "priv-1";
        enum "priv-10";
        enum "priv-11";
        enum "priv-12";
        enum "priv-13";
        enum "priv-14";
        enum "priv-15";
        enum "priv-2";
        enum "priv-3";
        enum "priv-4";
        enum "priv-5";
        enum "priv-6";
        enum "priv-7";
        enum "priv-8";
        enum "priv-9";
        enum "san-admin";
        enum "vdc-admin";
        enum "vdc-operator";
      }
      type string;
    }
  }

  typedef short-month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef itu-t-option2-type {
    type enumeration {
      enum "DUS";
      enum "EEC2";
      enum "PROV";
      enum "PRS";
      enum "PRTC";
      enum "RES";
      enum "SMC";
      enum "ST2";
      enum "ST3";
      enum "ST3E";
      enum "ST4";
      enum "STU";
      enum "TNC";
      enum "eEEC";
      enum "ePRTC";
    }
  }

  grouping interface-switchport-trunk-grouping {
    container trunk {
      container native {
        container vlan {
          leaf vlan-id {
            tailf:cli-drop-node-name;
            type uint16;
          }
          leaf tag {
            type empty;
          }
        }
      }
      leaf allow-multi-tag {
        type empty;
      }
      container allowed {
        container vlan {
          choice vlan-choice {
            leaf none {
              type empty;
            }
            leaf-list ids {
              tailf:cli-drop-node-name;
              tailf:cli-range-list-syntax;
              type vlan-list-type;
            }
          }
        }
      }
    }
  }

  grouping interface-switchport-grouping {
    container enable {
      tailf:cli-drop-node-name;
      leaf switchport {
        type boolean;
      }
    }
    container switchport {
      choice mode-choice {
        leaf mode {
          type enumeration {
            enum "access" {
              tailf:code-name "mode_access";
            }
            enum "fex-fabric";
            enum "trunk" {
              tailf:code-name "mode_trunk";
            }
            enum "dot1q-tunnel";
            enum "fabricpath";
          }
        }
        container private-vlan-mode {
          tailf:cli-drop-node-name;
          container mode {
            container private-vlan {
              choice mode-choice {
                leaf host {
                  type empty;
                }
                leaf promiscuous {
                  type empty;
                }
                leaf trunk {
                  type enumeration {
                    enum "promiscuous";
                    enum "secondary";
                  }
                }
              }
            }
          }
        }
      }
      container access {
        leaf vlan {
          type uint16;
        }
      }
      container block {
        leaf multicast {
          type empty;
        }
        leaf unicast {
          type empty;
        }
      }
      leaf description {
        tailf:cli-multi-value;
        type string;
      }
      leaf isolated {
        type empty;
      }
      leaf monitor {
        type empty;
      }
      uses interface-switchport-trunk-grouping;
      leaf virtual-ethernet-bridge {
        type empty;
      }
      container vlan {
        container mapping {
          leaf enable {
            type empty;
          }
          list map {
            tailf:cli-drop-node-name;
            tailf:cli-suppress-mode;
            tailf:cli-delete-when-empty;
            key "from to";
            leaf from {
              type vlan-list-type-all;
            }
            leaf to {
              type vlan-list-type;
            }
          }
          list dot1q-map {
            tailf:cli-drop-node-name;
            tailf:cli-suppress-mode;
            tailf:cli-delete-when-empty;
            tailf:cli-compact-syntax;
            tailf:cli-sequence-commands;
            tailf:cli-range-list-syntax;
            key "from";
            leaf from {
              type vlan-list-type-all;
            }
            leaf dot1q-tunnel {
              type empty;
            }
            leaf to {
              tailf:cli-drop-node-name;
              type vlan-list-type;
            }
          }
        }
      }
      container private-vlan {
        container association {
          list trunk {
            tailf:cli-suppress-mode;
            tailf:cli-delete-when-empty;
            key "primary";
            leaf primary {
              type uint16;
            }
            leaf secondary {
              tailf:cli-drop-node-name;
              type uint16;
            }
          }
        }
        container host-association {
          tailf:cli-compact-syntax;
          tailf:cli-sequence-commands {
            tailf:cli-reset-siblings;
          }
          leaf primary {
            tailf:cli-drop-node-name;
            type uint16;
          }
          leaf secondary {
            tailf:cli-drop-node-name;
            type uint16;
          }
        }
        container mapping {
          container primary-secondary {
            tailf:cli-drop-node-name;
            tailf:cli-compact-syntax;
            tailf:cli-sequence-commands {
              tailf:cli-reset-siblings;
            }
            leaf primary {
              tailf:cli-drop-node-name;
              type uint16;
            }
            leaf-list secondarys {
              tailf:cli-drop-node-name;
              tailf:cli-range-list-syntax;
              type uint16;
            }
          }
          list trunk {
            tailf:cli-suppress-mode;
            tailf:cli-delete-when-empty;
            key "primary";
            leaf primary {
              type uint16;
            }
            leaf-list secondarys {
              tailf:cli-drop-node-name;
              tailf:cli-range-list-syntax;
              type uint16;
            }
          }
        }
        container trunk {
          container native {
            leaf vlan {
              type uint16;
            }
          }
          container allowed {
            leaf-list vlan {
              tailf:cli-range-list-syntax;
              type uint16;
            }
          }
        }
      }
      container port-security-enable {
        tailf:cli-drop-node-name;
        leaf port-security {
          type empty;
        }
      }
      container port-security {
        container aging {
          leaf time {
            type uint16;
          }
          leaf type {
            type enumeration {
              enum "absolute";
              enum "inactivity";
            }
          }
        }
        leaf maximum {
          type uint16;
        }
        list mac-address {
          tailf:cli-suppress-mode;
          key "address";
          leaf address {
            type mac-address-type;
          }
        }
        leaf violation {
          type enumeration {
            enum "protect";
            enum "restrict";
            enum "shutdown";
          }
        }
      }
    }
  }

  grouping interface-switchport2-grouping {
    container switchport {
      leaf description {
        tailf:cli-multi-value;
        type string;
      }
      leaf mode {
        type enumeration {
          enum "E";
          enum "F";
          enum "SD";
          enum "auto" {
            tailf:code-name "switchport-grouping_mode_auto";
          }
        }
      }
      leaf speed {
        type enumeration {
          enum "1000" {
            tailf:code-name "switchport-grouping_1000";
          }
          enum "2000";
          enum "4000";
          enum "8000";
          enum "auto" {
            tailf:code-name "switchport-grouping_speed_auto";
          }
        }
      }
      container trunk {
        container allowed {
          leaf vsan {
            type string;
          }
        }
        leaf mode {
          type enumeration {
            enum "auto";
            enum "off";
            enum "on";
          }
        }
      }
    }
  }

  grouping interface-l2port-common-grouping {
    leaf duplex {
      type enumeration {
        enum "auto" {
          tailf:code-name "interface-port-channel-grouping-duplex_auto";
        }
        enum "full";
        enum "half";
      }
    }
    leaf speed {
      type enumeration {
        enum "10";
        enum "100";
        enum "1000";
        enum "10000";
        enum "40000";
        enum "100000";
        enum "auto";
        enum "2500";
        enum "5000";
        enum "25000";
        enum "50000";
        enum "200000";
        enum "400000";
      }
    }
    container negotiate {
      leaf auto {
        type boolean;
      }
    }
  }

  grouping interface-common-grouping {
    leaf description {
      tailf:cli-multi-value;
      type string;
    }
    container vrf {
      leaf member {
        type vrf-member-type;
      }
    }
    container logging {
      container event {
        container port {
          container linkstatus {
            tailf:alt-name "link-status";
            presence "UPDOWN and CHANGE messages";
            leaf default {
              type empty;
            }
          }
          container trunk-status {
            presence "TRUNK status messages";
            leaf default {
              type empty;
            }
          }
        }
      }
    }
    container ip {
      leaf forward {
        type empty;
      }
      list access-group {
        tailf:cli-suppress-mode;
        tailf:cli-delete-when-empty;
        key "direction";
        leaf name {
          tailf:cli-prefix-key;
          tailf:cli-drop-node-name;
          type string;
        }
        leaf direction {
          type enumeration {
            enum "in";
            enum "out";
          }
        }
      }
      choice static-or-dynamic {
        case static {
          container address {
            tailf:cli-compact-syntax;
            tailf:cli-sequence-commands;
            leaf ipaddr {
              tailf:cli-drop-node-name;
              type ip-mask;
            }
            leaf tag {
              type uint32;
            }
          }
          container secondary-addr {
            tailf:cli-drop-node-name;
            list address {
              tailf:cli-suppress-mode;
              tailf:cli-compact-syntax;
              key "ipaddr secaddr";
              leaf ipaddr {
                type ip-mask;
              }
              leaf secaddr {
                type enumeration {
                  enum "secondary";
                }
              }
              leaf tag {
                type uint32;
              }
            }
          }
        }
        case dynamic {
          container addr-dhcp {
            tailf:cli-drop-node-name;
            container address {
              leaf dhcp {
                type empty;
              }
            }
          }
        }
      }
      container arp {
        list address-list {
          tailf:cli-drop-node-name;
          tailf:cli-suppress-mode;
          tailf:cli-delete-when-empty;
          key "address";
          leaf address {
            type inet:ipv4-address;
          }
          leaf mac {
            tailf:cli-drop-node-name;
            type mac-address-type;
          }
        }
        leaf timeout {
          type uint16;
        }
        container gratuitous {
          container hsrp {
            leaf duplicate {
              type boolean;
            }
          }
          leaf request {
            type boolean;
          }
          leaf update {
            type boolean;
          }
        }
      }
      container dhcp {
        container relay {
          leaf subnet-broadcast {
            type empty;
          }
          list address {
            tailf:cli-suppress-mode;
            tailf:cli-delete-when-empty;
            key "id";
            leaf id {
              type inet:ipv4-address;
            }
            leaf use-vrf {
              type vrf-member-type;
            }
          }
          container information {
            leaf trusted {
              type empty;
            }
          }
          leaf source-interface {
            type string;
          }
        }
        leaf smart-relay {
          type empty;
        }
        container snooping {
          leaf trust {
            type empty;
          }
        }
      }
      leaf directed-broadcast {
        type empty;
      }
      container directed-broadcast-acl {
        tailf:cli-drop-node-name;
        leaf directed-broadcast {
          type string;
        }
      }
      container ospf {
        container authentication {
          presence "Authentication on the interface";
          tailf:cli-delete-when-empty;
          leaf key-chain {
            type string;
          }
          leaf authentication-type {
            tailf:cli-drop-node-name;
            type enumeration {
              enum "message-digest";
              enum "null";
            }
          }
        }
        container authentication-key {
          tailf:cli-compact-syntax;
          tailf:cli-sequence-commands;
          leaf encryption-type {
            tailf:cli-drop-node-name;
            tailf:cli-optional-in-sequence;
            type enumeration {
              enum "0";
              enum "3";
              enum "7";
            }
          }
          leaf key {
            tailf:cli-drop-node-name;
            type string;
          }
        }
        leaf bfd {
          type empty;
        }
        leaf cost {
          type uint16;
        }
        leaf dead-interval {
          type uint32;
        }
        leaf hello-interval {
          type uint16;
        }
        container message-digest-key {
          tailf:cli-compact-syntax;
          tailf:cli-sequence-commands;
          leaf key-id {
            tailf:cli-drop-node-name;
            type uint8;
          }
          leaf md5 {
            type empty;
          }
          leaf encryption-type {
            tailf:cli-drop-node-name;
            tailf:cli-optional-in-sequence;
            type enumeration {
              enum "0";
              enum "3";
              enum "7";
            }
          }
          leaf key {
            tailf:cli-drop-node-name;
            type string;
          }
        }
        leaf mtu-ignore {
          type empty;
        }
        leaf network {
          type enumeration {
            enum "broadcast";
            enum "point-to-point";
          }
        }
        leaf passive-interface {
          type boolean;
        }
        leaf priority {
          type uint8;
        }
        leaf retransmit-interval {
          type uint16;
        }
        leaf shutdown {
          type empty;
        }
        leaf transmit-delay {
          type uint16;
        }
      }
      leaf port-unreachable {
        type empty;
      }
      leaf redirects {
        type boolean;
      }
      container policy {
        leaf route-map {
          type string;
        }
      }
      leaf unreachables {
        type empty;
      }
      container port {
        list access-group {
          tailf:cli-suppress-mode;
          tailf:cli-delete-when-empty;
          key "direction";
          leaf name {
            tailf:cli-prefix-key;
            tailf:cli-drop-node-name;
            type string;
          }
          leaf direction {
            type enumeration {
              enum "in";
              enum "out";
            }
          }
        }
      }
      container router {
        container ospf {
          tailf:cli-compact-syntax;
          tailf:cli-sequence-commands;
          leaf name {
            tailf:cli-drop-node-name;
            type ospf-id-type;
          }
          leaf area {
            type ospf-area-type;
          }
        }
        leaf isis {
          type string;
        }
        list eigrp {
          tailf:cli-suppress-mode;
          tailf:cli-delete-when-empty;
          key "id";
          leaf id {
            type string;
          }
        }
        leaf rip {
          type string;
        }
      }
      container rip {
        list route-filter {
          tailf:cli-suppress-mode;
          tailf:cli-delete-when-empty;
          tailf:cli-compact-syntax;
          tailf:cli-sequence-commands {
            tailf:cli-reset-siblings;
          }
          key "direction";
          leaf direction {
            type enumeration {
              enum "in";
              enum "out";
            }
          }
          leaf type {
            tailf:cli-drop-node-name;
            tailf:cli-prefix-key;
            type enumeration {
              enum "prefix-list";
              enum "route-map";
            }
          }
          leaf name {
            tailf:cli-drop-node-name;
            tailf:cli-prefix-key;
            type string;
          }
        }
      }
      uses interface-ip-pim-grouping {
        augment "pim" {
          leaf dr-delay {
            type uint16;
          }
          container hello-authentication {
            container ah-md5 {
              choice ah-md5-choice {
                leaf plain {
                  tailf:alt-name "0";
                  type string;
                }
                leaf des3 {
                  tailf:alt-name "3";
                  type string;
                }
                leaf cisco_enc {
                  tailf:alt-name "7";
                  type string;
                }
                leaf unencrypted {
                  tailf:cli-drop-node-name;
                  type string;
                }
              }
            }
          }
          leaf strict-rfc-compliant {
            type empty;
          }
          choice bfd-inst-choice {
            leaf bfd-instance {
              type empty;
            }
            container disable-bfd-instance {
              tailf:cli-drop-node-name;
              container bfd-instance {
                leaf disable {
                  type empty;
                }
              }
            }
          }
        }
        refine "pim";
      }
      container igmp {
        container static-oif {
          list multicast-group {
            tailf:cli-drop-node-name;
            tailf:cli-suppress-mode;
            key "address source";
            leaf address {
              type inet:ipv4-address;
            }
            leaf source {
              tailf:cli-expose-key-name;
              type inet:ipv4-address;
            }
          }
          list multicast-group-nosrc {
            tailf:cli-drop-node-name;
            tailf:cli-suppress-mode;
            key "address";
            leaf address {
              type inet:ipv4-address;
            }
          }
          leaf route-map {
            type string;
          }
        }
        leaf query-max-response-time {
          type uint8;
        }
        leaf query-interval {
          type uint16;
        }
        leaf version {
          type uint8;
        }
        container join-group {
          list multicast-source {
            tailf:cli-drop-node-name;
            tailf:cli-suppress-mode;
            key "address source";
            leaf address {
              type inet:ipv4-address;
            }
            leaf source {
              tailf:cli-expose-key-name;
              type inet:ipv4-address;
            }
          }
          list multicast {
            tailf:cli-drop-node-name;
            tailf:cli-suppress-mode;
            key "address";
            leaf address {
              type inet:ipv4-address;
            }
          }
          leaf route-map {
            type string;
          }
        }
      }
      leaf nat {
        type enumeration {
          enum "inside";
          enum "outside";
        }
      }
      leaf proxy-arp {
        type empty;
      }
      container summary-address {
        list eigrp {
          tailf:cli-suppress-mode;
          tailf:cli-delete-when-empty;
          key "id addr";
          leaf id {
            type string;
          }
          leaf addr {
            type tailf:ipv4-address-and-prefix-length;
          }
        }
      }
      container bandwidth {
        uses eigrp-interface-config-list-grouping {
          augment "eigrp" {
            leaf bandwidth {
              tailf:cli-drop-node-name;
              type uint32;
            }
          }
        }
      }
      container passive-interface {
        uses eigrp-interface-config-list-grouping {
          augment "eigrp" {
            leaf suppress {
              tailf:cli-drop-node-name;
              type boolean;
            }
          }
        }
      }
      container delay {
        uses eigrp-interface-config-list-grouping {
          augment "eigrp" {
            leaf delay {
              tailf:cli-drop-node-name;
              type uint32;
            }
          }
        }
      }
      container distribute-list {
        uses eigrp-route-or-prefix-list-grouping;
      }
      container hold-time {
        uses eigrp-interface-config-list-grouping {
          augment "eigrp" {
            leaf down {
              tailf:cli-drop-node-name;
              type uint16;
            }
          }
        }
      }
      container hello-interval {
        uses eigrp-interface-config-list-grouping {
          augment "eigrp" {
            leaf hello {
              tailf:cli-drop-node-name;
              type uint16;
            }
          }
        }
      }
      container offset-list {
        uses eigrp-route-or-prefix-list-grouping {
          augment "eigrp" {
            leaf offset {
              tailf:cli-drop-node-name;
              type uint32;
            }
          }
        }
      }
      uses eigrp-interface-config-list-grouping {
        augment "eigrp" {
          leaf shutdown {
            type empty;
          }
        }
      }
      container verify {
        container unicast {
          container source {
            leaf reachable-via {
              type enumeration {
                enum "any";
                enum "rx";
              }
            }
          }
        }
        leaf source {
          type enumeration {
            enum "dhcp-snooping-vlan";
          }
        }
      }
      leaf unnumbered {
        type string;
      }
    }
    container ipv6 {
      container address {
        leaf dhcp {
          type empty;
        }
        choice addr-or-linklocal {
          list addresses {
            tailf:cli-drop-node-name;
            tailf:cli-suppress-mode;
            tailf:cli-delete-when-empty;
            tailf:cli-compact-syntax;
            tailf:cli-sequence-commands {
              tailf:cli-reset-siblings;
            }
            key "addr";
            leaf addr {
              type tailf:ipv6-address-and-prefix-length;
            }
            leaf eui64 {
              tailf:cli-optional-in-sequence;
              type empty;
            }
            leaf route-preference {
              tailf:cli-optional-in-sequence;
              type uint8;
            }
            leaf tag {
              tailf:cli-optional-in-sequence;
              type uint32;
            }
            leaf anycast {
              type empty;
            }
          }
          leaf use-link-local-only {
            type empty;
          }
        }
      }
      container have-secondary-address {
        tailf:cli-drop-node-name;
        container address {
          tailf:cli-compact-syntax;
          tailf:cli-sequence-commands;
          choice addr-or-linklocal {
            case has-addr {
              leaf addr {
                tailf:cli-drop-node-name;
                type tailf:ipv6-address-and-prefix-length;
              }
              leaf tag {
                type uint32;
              }
            }
            case has-linklocal {
              leaf use-link-local-only {
                type empty;
              }
            }
          }
        }
        container secondary-addr {
          tailf:cli-drop-node-name;
          list address {
            tailf:cli-suppress-mode;
            tailf:cli-compact-syntax;
            key "addr secaddr";
            leaf addr {
              type tailf:ipv6-address-and-prefix-length;
            }
            leaf secaddr {
              type enumeration {
                enum "secondary";
              }
            }
          }
        }
      }
      leaf link-local {
        type union {
          type inet:ipv6-address;
          type enumeration {
            enum "use-bia";
          }
        }
      }
      container nd {
        leaf managed-config-flag {
          type empty;
        }
        leaf other-config-flag {
          type empty;
        }
        list prefix {
          tailf:cli-suppress-mode;
          tailf:cli-delete-when-empty;
          tailf:cli-compact-syntax;
          tailf:cli-sequence-commands {
            tailf:cli-reset-siblings;
          }
          key "prefix";
          leaf prefix {
            type union {
              type tailf:ipv6-address-and-prefix-length;
              type enumeration {
                enum "default";
              }
            }
          }
          container valid-lifetime {
            tailf:cli-drop-node-name;
            tailf:cli-flatten-container;
            tailf:cli-compact-syntax;
            choice valid-lifetime-choice {
              leaf lifetime {
                tailf:cli-drop-node-name;
                type uint32;
              }
              leaf infinite {
                type empty;
              }
              leaf no-advertise {
                type empty;
              }
            }
          }
          container preferred-lifetime {
            tailf:cli-drop-node-name;
            tailf:cli-flatten-container;
            tailf:cli-compact-syntax;
            choice preferred-lifetime-choice {
              leaf lifetime {
                tailf:cli-drop-node-name;
                type uint32;
              }
              leaf infinite {
                type empty;
              }
            }
          }
          leaf no-autoconfig {
            tailf:cli-break-sequence-commands;
            type empty;
          }
          leaf no-onlink {
            type empty;
          }
          leaf off-link {
            type empty;
          }
        }
        leaf suppress-ra {
          type empty;
        }
        leaf redirects {
          type boolean;
        }
        leaf retrans-timer {
          type uint16;
        }
        leaf mtu {
          type uint16;
        }
        container ra-interval {
          tailf:cli-compact-syntax;
          tailf:cli-sequence-commands {
            tailf:cli-reset-siblings;
          }
          leaf interval {
            tailf:cli-drop-node-name;
            type uint16;
          }
          leaf min {
            type uint16;
          }
        }
        leaf ra-lifetime {
          type uint16;
        }
        container ra {
          leaf bootfile-url {
            type string;
          }
          container dns {
            container suppress-search-list {
              tailf:cli-drop-node-name;
              container search-list {
                leaf suppress {
                  type empty;
                }
              }
            }
            list search-list {
              tailf:cli-suppress-mode;
              tailf:cli-delete-when-empty;
              tailf:cli-compact-syntax;
              tailf:cli-sequence-commands {
                tailf:cli-reset-siblings;
              }
              unique "sequence";
              key "name";
              leaf name {
                type string;
              }
              leaf life-time {
                tailf:cli-drop-node-name;
                tailf:cli-optional-in-sequence;
                type union {
                  type uint32;
                  type enumeration {
                    enum "infinite";
                  }
                }
              }
              leaf sequence {
                mandatory true;
                type uint32;
              }
            }
            container suppress-server {
              tailf:cli-drop-node-name;
              container server {
                leaf suppress {
                  type empty;
                }
              }
            }
            list server {
              tailf:cli-suppress-mode;
              tailf:cli-delete-when-empty;
              tailf:cli-sequence-commands {
                tailf:cli-reset-siblings;
              }
              tailf:cli-compact-syntax;
              unique "sequence";
              key "address";
              leaf address {
                type inet:ipv6-address;
              }
              leaf life-time {
                tailf:cli-drop-node-name;
                tailf:cli-optional-in-sequence;
                type union {
                  type uint32;
                  type enumeration {
                    enum "infinite";
                  }
                }
              }
              leaf sequence {
                mandatory true;
                type uint32;
              }
            }
          }
          container route {
            leaf suppress {
              type empty;
            }
          }
        }
      }
      container neighbor {
        tailf:cli-compact-syntax;
        tailf:cli-sequence-commands;
        leaf address {
          tailf:cli-drop-node-name;
          type inet:ipv6-address;
        }
        leaf mac {
          tailf:cli-drop-node-name;
          type mac-address-type;
        }
      }
      leaf redirects {
        type boolean;
      }
      container policy {
        leaf route-map {
          type string;
        }
      }

      grouping if-ipv6-traffic-filter-grouping {
        list traffic-filter {
          tailf:cli-suppress-mode;
          tailf:cli-delete-when-empty;
          key "direction";
          leaf name {
            tailf:cli-drop-node-name;
            tailf:cli-prefix-key;
            type string;
          }
          leaf direction {
            type enumeration {
              enum "in";
              enum "out";
            }
          }
        }
      }
      container port {
        uses if-ipv6-traffic-filter-grouping;
      }
      uses if-ipv6-traffic-filter-grouping;
      container router {
        container ospfv3 {
          tailf:cli-compact-syntax;
          tailf:cli-sequence-commands;
          leaf name {
            tailf:cli-drop-node-name;
            type string;
          }
          leaf area {
            type union {
              type uint32;
              type inet:ipv4-address;
            }
          }
        }
        leaf isis {
          type string;
        }
      }
      uses interface-ip-pim-grouping {
        refine "pim";
      }
      container dhcp {
        container relay {
          list address {
            tailf:cli-suppress-mode;
            tailf:cli-delete-when-empty;
            tailf:cli-compact-syntax;
            key "addr use-vrf";
            leaf addr {
              type inet:ipv6-address;
            }
            leaf use-vrf {
              tailf:cli-expose-key-name;
              type vrf-member-type;
            }
          }
          leaf source-interface {
            type string;
          }
        }
      }
    }
    container ospfv3 {
      container authentication {
        choice authentication-choice {
          leaf disable {
            type empty;
          }
          container ipsec {
            tailf:cli-compact-syntax;
            tailf:cli-sequence-commands {
              tailf:cli-reset-siblings;
            }
            leaf spi {
              type uint32;
            }
            leaf alg {
              tailf:cli-drop-node-name;
              type enumeration {
                enum "md5";
                enum "sha1";
              }
            }
            leaf encryption-type {
              tailf:cli-drop-node-name;
              tailf:cli-optional-in-sequence;
              type enumeration {
                enum "0";
                enum "3";
                enum "7";
              }
            }
            leaf key {
              tailf:cli-drop-node-name;
              type string;
            }
          }
        }
      }
      leaf cost {
        type uint16;
      }
      leaf dead-interval {
        type uint16;
      }
      leaf hello-interval {
        type uint16;
      }
      leaf network {
        type enumeration {
          enum "broadcast";
          enum "point-to-point";
        }
      }
      leaf passive-interface {
        type boolean;
      }
      leaf priority {
        type uint8;
      }
      leaf retransmit-interval {
        type uint16;
      }
      leaf shutdown {
        type empty;
      }
      leaf transmit-delay {
        type uint16;
      }
      leaf bfd {
        type empty;
      }
      leaf instance {
        type uint8;
      }
    }
    container isis {
      leaf circuit-type {
        type enumeration {
          enum "level-1";
          enum "level-1-2";
          enum "level-2";
        }
      }
      leaf hello-padding {
        type boolean;
      }
      list metric {
        tailf:cli-suppress-mode;
        tailf:cli-delete-when-empty;
        key "link-type";
        leaf default-metric {
          tailf:cli-drop-node-name;
          tailf:cli-prefix-key;
          type uint32;
        }
        leaf link-type {
          type enumeration {
            enum "level-1";
            enum "level-2";
          }
        }
      }
      container ipv6 {
        list metric {
          tailf:cli-suppress-mode;
          tailf:cli-delete-when-empty;
          key "link-type";
          leaf default-metric {
            tailf:cli-drop-node-name;
            tailf:cli-prefix-key;
            type uint32;
          }
          leaf link-type {
            type enumeration {
              enum "level-1";
              enum "level-2";
            }
          }
        }
      }
      container passive-interface {
        tailf:cli-compact-syntax;
        tailf:cli-sequence-commands {
          tailf:cli-reset-siblings;
        }
        leaf pdu-type {
          tailf:cli-drop-node-name;
          type enumeration {
            enum "level-1";
            enum "level-1-2";
            enum "level-2";
          }
        }
        leaf suppress {
          tailf:cli-drop-node-name;
          type boolean;
        }
      }
      leaf passive {
        type enumeration {
          enum "level-1";
          enum "level-1-2";
          enum "level-2";
        }
      }
      choice bfd-choice {
        leaf bfd {
          type empty;
        }
        container bfd-disable {
          tailf:cli-drop-node-name;
          container bfd {
            leaf disable {
              type empty;
            }
          }
        }
      }
      container network {
        leaf point-to-point {
          type empty;
        }
      }
      container authentication {
        list key-chain {
          tailf:cli-suppress-mode;
          tailf:cli-delete-when-empty;
          tailf:cli-sequence-commands {
            tailf:cli-reset-siblings;
          }
          key "type";
          leaf name {
            tailf:cli-drop-node-name;
            tailf:cli-prefix-key;
            type string;
          }
          leaf type {
            type enumeration {
              enum "level-1";
              enum "level-2";
            }
          }
        }
      }
      container authentication-check {
        leaf level-1 {
          type boolean;
        }
        leaf level-2 {
          type boolean;
        }
      }
      list authentication-type {
        tailf:cli-suppress-mode;
        tailf:cli-delete-when-empty;
        tailf:cli-sequence-commands {
          tailf:cli-reset-siblings;
        }
        key "type";
        leaf auth-format {
          tailf:cli-drop-node-name;
          tailf:cli-prefix-key;
          type enumeration {
            enum "cleartext";
            enum "md5";
          }
        }
        leaf type {
          type enumeration {
            enum "level-1";
            enum "level-2";
          }
        }
      }
      list hello-interval {
        tailf:cli-suppress-mode;
        tailf:cli-delete-when-empty;
        key "link-type";
        leaf default-metric {
          tailf:cli-drop-node-name;
          tailf:cli-prefix-key;
          type uint16;
        }
        leaf link-type {
          type enumeration {
            enum "level-1";
            enum "level-2";
          }
        }
      }
      leaf lsp-interval {
        type uint16;
      }
    }
    container l2protocol {
      container tunnel {
        leaf cdp {
          type empty;
        }
        leaf dot1x {
          type empty;
        }
        leaf stp {
          type empty;
        }
        leaf vtp {
          type empty;
        }
        container drop-threshold {
          leaf cdp {
            type uint16;
          }
          leaf dot1x {
            type uint16;
          }
          leaf stp {
            type uint16;
          }
          leaf vtp {
            type uint16;
          }
        }
        container shutdown-threshold {
          leaf cdp {
            type uint16;
          }
          leaf dot1x {
            type uint16;
          }
          leaf stp {
            type uint16;
          }
          leaf vtp {
            type uint16;
          }
        }
        leaf lldp {
          type empty;
        }
        leaf lacp {
          type empty;
        }
        container vxlan {
          container vlan {
            choice vlan-choice {
              leaf none {
                type empty;
              }
              leaf-list ids {
                tailf:cli-drop-node-name;
                tailf:cli-range-list-syntax;
                type vlan-list-type;
              }
            }
          }
        }
      }
    }
  }

  grouping interface-ip-flow-grouping {
    container flow {
      list monitor {
        key "direction";
        tailf:cli-suppress-mode;
        tailf:cli-delete-when-empty;
        leaf name {
          tailf:cli-drop-node-name;
          tailf:cli-prefix-key;
          mandatory true;
          type string;
        }
        leaf direction {
          type enumeration {
            enum "input";
            enum "output";
          }
        }
        leaf sampler {
          type string;
        }
      }
    }
  }

  grouping interface-ip-pim-grouping {
    container pim {
      leaf border {
        type empty;
      }
      leaf dr-priority {
        type uint32;
      }
      leaf hello-interval {
        type uint32;
      }
      list jp-policy {
        tailf:cli-suppress-mode;
        tailf:cli-delete-when-empty;
        tailf:cli-compact-syntax;
        tailf:cli-sequence-commands {
          tailf:cli-reset-siblings;
        }
        key "direction";
        leaf direction {
          type enumeration {
            enum "in";
            enum "out";
          }
        }
        leaf prefix-list {
          tailf:cli-prefix-key;
          tailf:cli-optional-in-sequence;
          type empty;
        }
        leaf name {
          tailf:cli-drop-node-name;
          tailf:cli-prefix-key;
          mandatory true;
          type string;
        }
      }
      container neighbor-policy {
        choice neighbor-policy-choice {
          leaf route-map-name {
            tailf:cli-drop-node-name;
            type string;
          }
          leaf prefix-list {
            type string;
          }
        }
      }
      leaf sparse-mode {
        type empty;
      }
    }
  }

  grouping interface-bfd-grouping {
    uses bfd-grouping {
      augment "bfd" {
        leaf per-link {
          type empty;
        }
        container authentication {
          container Keyed-SHA1 {
            tailf:cli-compact-syntax;
            tailf:cli-sequence-commands {
              tailf:cli-reset-siblings;
            }
            leaf key-id {
              type uint8;
            }
            leaf key-type {
              tailf:cli-drop-node-name;
              type enumeration {
                enum "hex-key";
                enum "key";
              }
            }
            leaf key {
              tailf:cli-drop-node-name;
              type string;
            }
          }
        }
        list neighbor {
          tailf:cli-suppress-mode;
          key "src-ip dest-ip";
          leaf src-ip {
            tailf:cli-expose-key-name;
            tailf:cli-suppress-range;
            type union {
              type inet:ipv4-address;
              type inet:ipv6-address;
            }
          }
          leaf dest-ip {
            tailf:cli-expose-key-name;
            type union {
              type inet:ipv4-address;
              type inet:ipv6-address;
            }
          }
        }
      }
    }
  }

  grouping interface-eth-pc-bfd-grouping {
    container enable-disable-bfd {
      tailf:cli-drop-node-name;
      leaf bfd {
        type boolean;
      }
      container bfd-ip {
        tailf:cli-drop-node-name;
        container bfd {
          leaf ipv4 {
            type boolean;
          }
          leaf ipv6 {
            type boolean;
          }
        }
      }
    }
    uses interface-bfd-grouping;
  }

  grouping interface-vlan-grouping {
    uses interface-ether-and-vlan-grouping;
    leaf medium {
      type enumeration {
        enum "broadcast" {
          tailf:code-name "medium_broadcast";
        }
        enum "p2p";
      }
    }
    leaf autostate {
      type boolean;
    }
    container carrier-delay {
      choice delay-choice {
        leaf delay-seconds {
          tailf:cli-drop-node-name;
          type uint8;
        }
        leaf msec {
          type uint16;
        }
      }
    }
    leaf management {
      type boolean;
    }
    container fabric {
      container forwarding {
        leaf mode {
          type enumeration {
            enum "anycast-gateway";
          }
        }
      }
    }
    uses interface-vrrpv3-grouping;
  }

  grouping interface-vrrpv3-grouping {
    list vrrpv3 {
      key "vr address-family";
      leaf vr {
        type uint8;
      }
      leaf address-family {
        tailf:cli-expose-key-name;
        type enumeration {
          enum "ipv4";
          enum "ipv6";
        }
      }
      container address {
        list ipv4-address-list {
          tailf:cli-drop-node-name;
          tailf:cli-suppress-mode;
          tailf:cli-delete-when-empty;
          key "address type";
          leaf address {
            type inet:ipv4-address;
          }
          leaf type {
            type enumeration {
              enum "primary";
              enum "secondary";
            }
          }
        }
        list ipv6-address-list {
          tailf:cli-drop-node-name;
          tailf:cli-suppress-mode;
          tailf:cli-delete-when-empty;
          key "address";
          leaf address {
            type inet:ipv6-address;
          }
          leaf primary {
            type empty;
          }
        }
      }
      container preempt {
        container delay {
          leaf minimum {
            type uint16;
          }
        }
      }
      leaf priority {
        type uint8;
      }
    }
  }

  grouping interface-ether-and-vlan-grouping {
    container bandwidth {
      container inherited {
        tailf:cli-drop-node-name;
        tailf:cli-sequence-commands {
          tailf:cli-reset-siblings;
        }
        tailf:cli-compact-syntax;
        leaf inherit {
          type empty;
        }
        leaf bandwidth {
          tailf:cli-drop-node-name;
          type uint32;
        }
      }
      leaf bandwidth {
        tailf:cli-drop-node-name;
        type uint32;
      }
    }
    container load-interval {
      leaf interval {
        tailf:cli-drop-node-name;
        type uint16;
      }
      list counter {
        tailf:cli-suppress-mode;
        tailf:cli-delete-when-empty;
        key "id";
        leaf id {
          type uint8;
        }
        leaf interval {
          tailf:cli-drop-node-name;
          type uint16;
        }
      }
    }
    leaf mtu {
      type uint16;
    }
    leaf delay {
      type uint32;
    }
    leaf mac-address {
      type mac-address-type;
    }
    container hsrp {
      leaf version {
        type uint16;
      }
      container delay {
        tailf:cli-compact-syntax;
        leaf minimum {
          type uint16;
        }
        leaf reload {
          type uint16;
        }
      }
      leaf bfd {
        type boolean;
      }
      leaf mac-refresh {
        type uint16;
      }
      list hsrp-list {
        tailf:cli-drop-node-name;
        key "id addr_type";
        leaf id {
          type uint16;
        }
        leaf addr_type {
          type enumeration {
            enum "ipv4";
            enum "ipv6";
          }
        }
        leaf follow {
          type string;
        }
        container authentication {
          choice text-or-md5 {
            leaf text {
              type string;
            }
            container md5 {
              choice chain-or-string {
                leaf key-chain {
                  type string;
                }
                container key-string {
                  tailf:cli-compact-syntax;
                  tailf:cli-sequence-commands;
                  leaf key-type {
                    tailf:cli-drop-node-name;
                    tailf:cli-optional-in-sequence;
                    type enumeration {
                      enum "0";
                      enum "7";
                    }
                  }
                  leaf key-value {
                    tailf:cli-drop-node-name;
                    type string;
                  }
                }
              }
            }
          }
        }
        list ip {
          tailf:cli-suppress-mode;
          tailf:cli-delete-when-empty;
          key "address";
          leaf address {
            type union {
              type inet:ipv4-address;
              type inet:ipv6-address;
              type tailf:ipv4-address-and-prefix-length;
              type enumeration {
                enum "autoconfig";
              }
            }
          }
          leaf secondary {
            type empty;
          }
        }
        leaf mac-address {
          type mac-address-type;
        }
        container timers {
          tailf:cli-compact-syntax;
          tailf:cli-sequence-commands {
            tailf:cli-reset-siblings;
          }
          choice hello-choice {
            leaf hello-msec {
              tailf:alt-name "msec";
              type uint16;
            }
            leaf hello-seconds {
              tailf:cli-drop-node-name;
              type uint8;
            }
          }
          choice hold-choice {
            leaf hold-msec {
              tailf:alt-name "msec";
              type uint16;
            }
            leaf hold-seconds {
              tailf:cli-drop-node-name;
              type uint8;
            }
          }
        }
        list track {
          tailf:cli-suppress-mode;
          tailf:cli-delete-when-empty;
          key "id";
          leaf id {
            type uint16;
          }
          leaf decrement {
            type uint8;
          }
        }
        container preempt {
          presence "true";
          container delay {
            tailf:cli-compact-syntax;
            leaf minimum {
              type uint16;
            }
            leaf reload {
              type uint16;
            }
            leaf sync {
              type uint16;
            }
          }
        }
        choice prio-choice {
          leaf priority {
            type uint8;
          }
          container prio-and-threshold {
            tailf:cli-drop-node-name;
            tailf:cli-compact-syntax;
            tailf:cli-sequence-commands {
              tailf:cli-reset-siblings;
            }
            leaf priority {
              type uint8;
            }
            leaf forwarding-threshold {
              type empty;
            }
            leaf lower {
              type uint8;
            }
            leaf upper {
              type uint8;
            }
          }
        }
        leaf name {
          type string;
        }
      }
    }
    list vrrp {
      key "vr";
      leaf vr {
        type uint8;
      }
      leaf address {
        type inet:ipv4-address;
      }
      leaf advertisement-interval {
        type uint8;
      }
      container authentication {
        choice authentication-choice {
          leaf word {
            tailf:cli-drop-node-name;
            type string;
          }
          leaf text {
            type string;
          }
        }
      }
      leaf preempt {
        type empty;
      }
      container priority {
        tailf:cli-compact-syntax;
        tailf:cli-sequence-commands;
        leaf value {
          tailf:cli-drop-node-name;
          type uint8;
        }
        container forwarding-threshold {
          tailf:cli-compact-syntax;
          tailf:cli-flatten-container;
          tailf:cli-sequence-commands;
          leaf lower {
            type uint8;
          }
          leaf upper {
            type uint8;
          }
        }
      }
      leaf shutdown {
        type empty;
      }
      container track {
        tailf:cli-compact-syntax;
        tailf:cli-sequence-commands;
        choice track {
          case a {
            leaf interface {
              type string;
            }
            leaf priority {
              type uint8;
            }
          }
          case b {
            list object {
              tailf:cli-drop-node-name;
              tailf:cli-suppress-mode;
              tailf:cli-delete-when-empty;
              key "id";
              leaf id {
                type uint16;
              }
              leaf decrement {
                type uint8;
              }
            }
          }
        }
      }
    }
    container snmp {
      container trap {
        leaf link-status {
          type boolean;
        }
      }
    }
    container evpn {
      leaf multisite {
        type enumeration {
          enum "dci-tracking";
          enum "fabric-tracking";
        }
      }
    }
    container mpls {
      container enable-ip {
        tailf:cli-drop-node-name;
        leaf ip {
          type empty;
        }
      }
      container ip {
        leaf forwarding {
          type empty;
        }
      }
    }
    container inherit {
      leaf port-profile {
        type string;
      }
    }
  }

  grouping if-service-policy-grouping {
    container service-policy {
      container type {
        container qos {
          container input {
            tailf:cli-compact-syntax;
            tailf:cli-sequence-commands;
            leaf name {
              tailf:cli-drop-node-name;
              type policy-map-name-type;
            }
            leaf no-stats {
              type empty;
            }
          }
          container output {
            tailf:cli-compact-syntax;
            tailf:cli-sequence-commands;
            leaf name {
              tailf:cli-drop-node-name;
              type policy-map-name-type;
            }
            leaf no-stats {
              type empty;
            }
          }
        }
      }
    }
  }

  grouping interface-ethernet-grouping {
    uses interface-ether-and-vlan-grouping {
      refine "evpn";
    }
    leaf medium {
      type enumeration {
        enum "broadcast" {
          tailf:code-name "medium_broadcast";
        }
        enum "p2p";
      }
    }
    container fex {
      leaf associate {
        type uint8;
      }
    }
    container priority-flow-control {
      leaf mode {
        type enumeration {
          enum "auto" {
            tailf:code-name "prio_flow_control_auto";
          }
          enum "off" {
            tailf:code-name "prio_flow_off";
          }
          enum "on" {
            tailf:code-name "prio_flow_on";
          }
        }
      }
    }
    container flowcontrol {
      leaf receive {
        type enumeration {
          enum "off";
          enum "on";
          enum "desired";
        }
      }
      leaf send {
        type enumeration {
          enum "off";
          enum "on";
          enum "desired";
        }
      }
    }
    container service {
      list instance {
        tailf:cli-sequence-commands;
        tailf:cli-compact-syntax;
        key "service-id";
        leaf service-id {
          tailf:cli-optional-in-sequence;
          type union {
            type uint16;
            type string;
          }
        }
        container vni {
          tailf:cli-hide-in-submode;
          tailf:cli-flatten-container;
          presence "Virtual Network Identifier";
          leaf default {
            type empty;
          }
        }
        leaf shutdown {
          tailf:cli-break-sequence-commands;
          type empty;
        }
        leaf description {
          tailf:cli-break-sequence-commands;
          tailf:cli-multi-value;
          type string;
        }
        container encapsulation {
          choice encapsulation-choice {
            container dynamic {
              choice dynamic-choice {
                container frame-snoop {
                  leaf profile {
                    type string;
                  }
                }
                container vdp {
                  presence "Enable VDP auto-configuration for this vsi";
                  leaf-list exception-list {
                    tailf:cli-range-list-syntax;
                    type uint16;
                  }
                }
              }
            }
            container profile {
              tailf:cli-compact-syntax;
              tailf:cli-sequence-commands;
              leaf name {
                tailf:cli-drop-node-name;
                type string;
              }
              leaf default {
                type empty;
              }
            }
            container dot1q-profile {
              tailf:cli-drop-node-name;
              list profile {
                key "name";
                leaf name {
                  type string;
                }
                list dot1q {
                  tailf:cli-suppress-mode;
                  tailf:cli-delete-when-empty;
                  key "vlan-id";
                  leaf vlan-id {
                    type uint16;
                  }
                }
              }
            }
          }
          container untagged {
            container dot1q {
              tailf:cli-compact-syntax;
              tailf:cli-sequence-commands {
                tailf:cli-reset-siblings;
              }
              leaf vlan-id {
                tailf:cli-drop-node-name;
                type uint16;
              }
              leaf vni {
                type uint32;
              }
            }
          }
        }
      }
    }
    container service-policy {
      container type {
        container qos {
          container input {
            tailf:cli-compact-syntax;
            tailf:cli-sequence-commands;
            leaf name {
              tailf:cli-drop-node-name;
              type policy-map-name-type;
            }
            leaf no-stats {
              type empty;
            }
          }
          container output {
            tailf:cli-compact-syntax;
            tailf:cli-sequence-commands;
            leaf name {
              tailf:cli-drop-node-name;
              type policy-map-name-type;
            }
            leaf no-stats {
              type empty;
            }
          }
        }
        container queuing {
          container input {
            tailf:cli-compact-syntax;
            tailf:cli-sequence-commands;
            leaf name {
              tailf:cli-drop-node-name;
              type policy-map-name-type;
            }
            leaf no-stats {
              type empty;
            }
          }
          container output {
            tailf:cli-compact-syntax;
            tailf:cli-sequence-commands;
            leaf name {
              tailf:cli-drop-node-name;
              type policy-map-name-type;
            }
            leaf no-stats {
              type empty;
            }
          }
        }
        leaf network-qos {
          type policy-map-name-type;
        }
      }
    }
    container spanning-tree {
      leaf bpdufilter {
        type enumeration {
          enum "disable" {
            tailf:code-name "bdufilter_disable";
          }
          enum "enable" {
            tailf:code-name "bdufilter_enable";
          }
        }
      }
      leaf bpduguard {
        type enumeration {
          enum "disable" {
            tailf:code-name "bduguard_disable";
          }
          enum "enable" {
            tailf:code-name "bduguard_enable";
          }
        }
      }
      leaf cost {
        type union {
          type uint32;
          type enumeration {
            enum "auto" {
              tailf:code-name "spanning-tree-cost-type-auto";
            }
          }
        }
      }
      leaf guard {
        type enumeration {
          enum "loop";
          enum "none";
          enum "root";
        }
      }
      leaf link-type {
        type enumeration {
          enum "auto" {
            tailf:code-name "link_type_auto";
          }
          enum "none";
          enum "root";
          enum "point-to-point";
          enum "shared";
        }
      }
      container mst {
        list port {
          tailf:cli-drop-node-name;
          tailf:cli-suppress-mode;
          tailf:cli-delete-when-empty;
          key "range";
          leaf range {
            type string;
          }
          leaf cost {
            type union {
              type uint32;
              type enumeration {
                enum "auto" {
                  tailf:code-name "mst_cost_type_auto";
                }
              }
            }
          }
          leaf port-priority {
            type uint8;
          }
        }
        leaf pre-standard {
          type empty;
        }
        container simulate {
          container pvst {
            presence "Enable PVST simulation";
            leaf disable {
              type empty;
            }
          }
        }
      }
      container port {
        tailf:cli-sequence-commands {
          tailf:cli-reset-siblings;
        }
        tailf:cli-compact-syntax;
        leaf type {
          type enumeration {
            enum "edge";
            enum "network";
            enum "normal";
          }
        }
        leaf trunk {
          type empty;
        }
      }
      leaf port-priority {
        type uint8;
      }
      list vlan {
        tailf:cli-suppress-mode;
        tailf:cli-delete-when-empty;
        tailf:cli-range-list-syntax;
        key "id";
        leaf id {
          type uint16;
        }
        leaf cost {
          type uint32;
        }
        leaf port-priority {
          type uint8;
        }
      }
    }
    container storm-control {
      container broadcast {
        leaf level {
          type decimal64 {
            fraction-digits 2;
          }
        }
        container level-pps {
          tailf:cli-drop-node-name;
          container level {
            leaf pps {
              type uint32;
            }
          }
        }
      }
      container unicast {
        leaf level {
          type decimal64 {
            fraction-digits 2;
          }
        }
        container level-pps {
          tailf:cli-drop-node-name;
          container level {
            leaf pps {
              type uint32;
            }
          }
        }
      }
      container multicast {
        leaf level {
          type decimal64 {
            fraction-digits 2;
          }
        }
        container level-pps {
          tailf:cli-drop-node-name;
          container level {
            leaf pps {
              type uint32;
            }
          }
        }
      }
      container action {
        leaf shutdown {
          type empty;
        }
        leaf trap {
          type empty;
        }
      }
    }
    container mac {
      container port {
        leaf access-group {
          type string;
        }
      }
    }
    leaf port-type {
      type string;
    }
    uses mvr-cfg-grouping;
    container mvr-type {
      leaf receiver {
        type empty;
      }
      leaf source {
        type empty;
      }
    }
  }

  grouping ethernet-and-port-channel-grouping {
    container encapsulation {
      container dot1Q {
        tailf:cli-sequence-commands;
        tailf:cli-compact-syntax;
        tailf:cli-case-insensitive;
        leaf vlan-id {
          tailf:cli-drop-node-name;
          type uint16;
        }
        leaf second-dot1q {
          tailf:cli-optional-in-sequence;
          type union {
            type enumeration {
              enum "any";
            }
            type string;
          }
        }
        leaf native {
          type empty;
        }
      }
    }
    container untagged {
      leaf cos {
        type uint8;
      }
    }
    container vpc {
      leaf port-channel-number {
        tailf:cli-drop-node-name;
        type uint16;
      }
      leaf peer-link {
        type empty;
      }
      leaf orphan-port {
        type enumeration {
          enum "suspend";
        }
      }
    }
    container cts {
      container manual {
        tailf:cli-add-mode;
        container policy {
          container dynamic {
            leaf identity {
              type string;
            }
          }
          container static {
            tailf:cli-compact-syntax;
            tailf:cli-sequence-commands {
              tailf:cli-reset-siblings;
            }
            leaf sgt {
              type uint16;
            }
            leaf trusted {
              type empty;
            }
          }
        }
      }
    }
  }

  grouping interface-port-channel-grouping {
    container lacp {
      container mode {
        leaf delay {
          type empty;
        }
      }
      leaf graceful-convergence {
        type boolean;
      }
      leaf suspend-individual {
        type boolean;
      }
      container conf {
        tailf:cli-drop-node-name;
        container suspend-individual {
          leaf pxe {
            type boolean;
          }
        }
      }
      leaf min-links {
        type uint8;
      }
      leaf max-bundle {
        type uint8;
      }
      leaf vpc-convergence {
        type empty;
      }
    }
    container port-channel {
      leaf min-links {
        type uint8;
      }
      container bfd {
        leaf start {
          type uint16;
        }
        leaf destination {
          type inet:ipv4-address;
        }
        leaf track-member-link {
          type empty;
        }
      }
    }
    container hardware {
      leaf multicast {
        type enumeration {
          enum "hw-hash";
        }
      }
    }
    leaf link-state-trap {
      type empty;
    }
    leaf vem {
      type uint16;
    }
    list ethernet-segment {
      key "es-id";
      leaf es-id {
        type uint32;
      }
      leaf system-mac {
        type string;
      }
    }
  }

  grouping interface-fc-and-san-grouping {
    container fcdomain {
      container rcf-reject {
        leaf vsan {
          type string;
        }
      }
    }
    container fspf {
      container cost {
        tailf:cli-sequence-commands {
          tailf:cli-reset-siblings;
        }
        tailf:cli-compact-syntax;
        leaf cost {
          tailf:cli-drop-node-name;
          type uint16;
        }
        leaf vsan {
          type string;
        }
      }
      container dead-interval {
        tailf:cli-sequence-commands {
          tailf:cli-reset-siblings;
        }
        tailf:cli-compact-syntax;
        leaf cost {
          tailf:cli-drop-node-name;
          type uint16;
        }
        leaf vsan {
          type string;
        }
      }
      container hello-interval {
        tailf:cli-sequence-commands {
          tailf:cli-reset-siblings;
        }
        tailf:cli-compact-syntax;
        leaf cost {
          tailf:cli-drop-node-name;
          type uint16;
        }
        leaf vsan {
          type string;
        }
      }
      container passive {
        leaf vsan {
          type string;
        }
      }
      container retransmit-interval {
        tailf:cli-sequence-commands {
          tailf:cli-reset-siblings;
        }
        tailf:cli-compact-syntax;
        leaf cost {
          tailf:cli-drop-node-name;
          type uint16;
        }
        leaf vsan {
          type string;
        }
      }
    }
    leaf shutdown {
      type empty;
    }
  }

  grouping policy-map-police-action-grouping {
    choice conform-action {
      leaf drop {
        type empty;
      }
      leaf transmit {
        type empty;
      }
    }
  }

  grouping policy-map-class-qos-grouping {
    container set {
      leaf cos {
        type uint8;
      }
      leaf dscp {
        type dscp-type;
      }
      leaf precedence {
        type uint8;
      }
      leaf qos-group {
        type uint8;
      }
    }
    container police {
      tailf:cli-compact-syntax;
      tailf:cli-sequence-commands {
        tailf:cli-reset-siblings;
      }
      leaf cir {
        type union {
          type uint64;
          type enumeration {
            enum "percent";
          }
        }
      }
      leaf cir-percent {
        tailf:cli-drop-node-name;
        type uint8;
      }
      leaf cir-type {
        tailf:cli-drop-node-name;
        type xfer-speed-type;
      }
      leaf bc {
        type uint32;
      }
      leaf bc-type {
        tailf:cli-drop-node-name;
        type burst-type;
      }
      container pir {
        tailf:cli-optional-in-sequence;
        tailf:cli-flatten-container;
        tailf:cli-compact-syntax;
        tailf:cli-sequence-commands {
          tailf:cli-reset-siblings;
        }
        leaf value {
          tailf:cli-drop-node-name;
          type uint64;
        }
        leaf cir-type {
          tailf:cli-drop-node-name;
          type xfer-speed-type;
        }
        leaf be {
          type uint32;
        }
        leaf be-type {
          tailf:cli-drop-node-name;
          type burst-type;
        }
      }
      container conform {
        tailf:cli-flatten-container;
        uses policy-map-police-action-grouping;
      }
      container exceed {
        tailf:cli-optional-in-sequence;
        tailf:cli-flatten-container;
        uses policy-map-police-action-grouping;
      }
      container violate {
        tailf:cli-flatten-container;
        uses policy-map-police-action-grouping;
      }
    }
  }

  grouping common-base-redistribute-grouping {
    container default-information {
      container originate {
        tailf:cli-compact-syntax;
        tailf:cli-sequence-commands;
        presence "true";
        leaf always {
          tailf:cli-optional-in-sequence;
          type empty;
        }
        leaf route-map {
          type string;
        }
      }
    }
    container redistribute {

      grouping route-map-grouping {
        leaf route-map {
          type string;
        }
      }
      container am {
        uses route-map-grouping;
      }
      list bgp {
        tailf:cli-suppress-mode;
        tailf:cli-delete-when-empty;
        key "as-number";
        leaf as-number {
          type asn-type;
        }
        uses route-map-grouping;
      }
      container direct {
        uses route-map-grouping;
      }
      list eigrp {
        tailf:cli-suppress-mode;
        tailf:cli-delete-when-empty;
        key "tag";
        leaf tag {
          type string;
        }
        uses route-map-grouping;
      }
      list isis {
        tailf:cli-suppress-mode;
        tailf:cli-delete-when-empty;
        key "tag";
        leaf tag {
          type string;
        }
        uses route-map-grouping;
      }
      container lisp {
        uses route-map-grouping;
      }
      container maximum-prefix {
        tailf:cli-compact-syntax;
        tailf:cli-sequence-commands {
          tailf:cli-reset-all-siblings;
        }
        leaf max-number {
          tailf:cli-drop-node-name;
          type uint16;
        }
        leaf threshold {
          tailf:cli-drop-node-name;
          tailf:cli-optional-in-sequence;
          type uint8;
        }
        choice warning-or-withdraw {
          case warning-only {
            leaf warning-only {
              type empty;
            }
          }
          case withdraw {
            leaf withdraw {
              type empty;
            }
            leaf retry {
              tailf:cli-drop-node-name;
              type uint8;
            }
          }
        }
        leaf timeout {
          tailf:cli-drop-node-name;
          type uint16;
        }
      }
      list ospf {
        tailf:cli-suppress-mode;
        tailf:cli-delete-when-empty;
        key "tag";
        leaf tag {
          type string;
        }
        uses route-map-grouping;
      }
      list ospfv3 {
        tailf:cli-suppress-mode;
        tailf:cli-delete-when-empty;
        key "tag";
        leaf tag {
          type string;
        }
        uses route-map-grouping;
      }
      list rip {
        tailf:cli-suppress-mode;
        tailf:cli-delete-when-empty;
        key "tag";
        leaf tag {
          type string;
        }
        uses route-map-grouping;
      }
      container static {
        uses route-map-grouping;
      }
    }
    container table-map {
      tailf:cli-compact-syntax;
      tailf:cli-sequence-commands {
        tailf:cli-reset-siblings;
      }
      leaf name {
        tailf:cli-drop-node-name;
        type string;
      }
      leaf filter {
        type empty;
      }
    }
  }

  grouping common-router-redistribute-grouping {
    uses common-base-redistribute-grouping {
      refine "default-information/originate/always";
      refine "default-information/originate/route-map";
    }
    leaf distance {
      type uint32;
    }
    leaf maximum-paths {
      type uint32;
    }
  }

  grouping common-router-redistribute-grouping-rip {
    container redistribute {

      grouping route-map-grouping {
        leaf route-map {
          type string;
        }
      }
      list bgp {
        tailf:cli-suppress-mode;
        tailf:cli-delete-when-empty;
        key "as-number";
        leaf as-number {
          type asn-type;
        }
        uses route-map-grouping;
      }
      container direct {
        uses route-map-grouping;
      }
      list eigrp {
        tailf:cli-suppress-mode;
        tailf:cli-delete-when-empty;
        key "tag";
        leaf tag {
          type string;
        }
        uses route-map-grouping;
      }
      list isis {
        tailf:cli-suppress-mode;
        tailf:cli-delete-when-empty;
        key "tag";
        leaf tag {
          type string;
        }
        uses route-map-grouping;
      }
      container lisp {
        uses route-map-grouping;
      }
      container maximum-prefix {
        tailf:cli-compact-syntax;
        tailf:cli-sequence-commands {
          tailf:cli-reset-all-siblings;
        }
        leaf max-number {
          tailf:cli-drop-node-name;
          type uint16;
        }
        leaf threshold {
          tailf:cli-drop-node-name;
          tailf:cli-optional-in-sequence;
          type uint8;
        }
        choice warning-or-withdraw {
          case warning-only {
            leaf warning-only {
              type empty;
            }
          }
          case withdraw {
            leaf withdraw {
              type empty;
            }
            leaf retry {
              tailf:cli-drop-node-name;
              type uint8;
            }
          }
        }
        leaf timeout {
          tailf:cli-drop-node-name;
          type uint16;
        }
      }
      list ospf {
        tailf:cli-suppress-mode;
        tailf:cli-delete-when-empty;
        key "tag";
        leaf tag {
          type string;
        }
        uses route-map-grouping;
      }
      list ospfv3 {
        tailf:cli-suppress-mode;
        tailf:cli-delete-when-empty;
        key "tag";
        leaf tag {
          type string;
        }
        uses route-map-grouping;
      }
      list rip {
        tailf:cli-suppress-mode;
        tailf:cli-delete-when-empty;
        key "tag";
        leaf tag {
          type string;
        }
        uses route-map-grouping;
      }
      container static {
        uses route-map-grouping;
      }
    }
    container default-information {
      tailf:cli-compact-syntax;
      tailf:cli-sequence-commands {
        tailf:cli-reset-siblings;
      }
      leaf originate {
        type empty;
      }
      leaf always {
        tailf:cli-optional-in-sequence;
        type empty;
      }
      leaf route-map {
        type string;
      }
    }
    leaf distance {
      type uint32;
    }
    leaf maximum-paths {
      type uint32;
    }
    leaf default-metric {
      type uint8;
    }
  }

  grouping ospfv3-address-family-grouping {
    container address-family {
      container ipv6 {
        container unicast {
          tailf:cli-add-mode;
          uses common-router-redistribute-grouping;
          uses ospf-area-grouping;
          leaf default-metric {
            type uint32;
          }
          list summary-address {
            tailf:cli-suppress-mode;
            tailf:cli-delete-when-empty;
            key "address";
            leaf address {
              type tailf:ipv6-address-and-prefix-length;
            }
          }
          container timers {
            container throttle {
              uses ospf-timers-throttle-spf-grouping;
            }
          }
        }
      }
    }
  }

  grouping ospf-area-grouping {
    list area {
      tailf:cli-suppress-mode;
      tailf:cli-delete-when-empty;
      key "id";
      leaf id {
        tailf:cli-suppress-range;
        type ospf-area-type;
      }
      container authentication {
        presence "Enable authentication";
        leaf message-digest {
          type empty;
        }
      }
      leaf default-cost {
        type uint32;
      }
      choice nssa-or-stub {
        container nssa {
          tailf:cli-compact-syntax;
          presence "Specify a NSSA area";
          container default-information-originate {
            tailf:cli-flatten-container;
            presence "true";
            leaf route-map {
              type string;
            }
          }
          leaf no-redistribution {
            type empty;
          }
          leaf no-summary {
            type empty;
          }
        }
        container stub {
          presence "Specify a stub area";
          leaf no-summary {
            type empty;
          }
        }
      }
      container nssa-translate {
        tailf:cli-drop-node-name;
        container nssa {
          container translate {
            leaf type7 {
              type enumeration {
                enum "suppress-fa";
                enum "supress-fa";
                enum "always";
                enum "never";
              }
            }
          }
        }
      }
      container filter-list {
        list route-map {
          tailf:cli-suppress-mode;
          tailf:cli-delete-when-empty;
          key "direction";
          leaf name {
            tailf:cli-prefix-key;
            tailf:cli-drop-node-name;
            type string;
          }
          leaf direction {
            type enumeration {
              enum "in";
              enum "out";
            }
          }
        }
      }
      list range {
        tailf:cli-suppress-mode;
        tailf:cli-delete-when-empty;
        tailf:cli-compact-syntax;
        key "ip";
        leaf ip {
          type tailf:ipv4-address-and-prefix-length;
        }
        leaf not-advertise {
          type empty;
        }
        leaf cost {
          type uint32;
        }
      }
      container range-ipv6 {
        tailf:cli-drop-node-name;
        list range {
          tailf:cli-suppress-mode;
          tailf:cli-compact-syntax;
          key "ipv6";
          leaf ipv6 {
            type tailf:ipv6-address-and-prefix-length;
          }
          leaf not-advertise {
            type empty;
          }
          leaf cost {
            type uint32;
          }
        }
      }
      list sham-link {
        tailf:cli-suppress-mode;
        tailf:cli-delete-when-empty;
        key "source dest";
        leaf source {
          type inet:ipv4-address;
        }
        leaf dest {
          type inet:ipv4-address;
        }
        leaf cost {
          type uint16;
        }
      }
      list virtual-link {
        must "not(../nssa)" {
          error-message "The area is configured as NSSA area already";
        }
        must "not(../stub)" {
          error-message "The area is configured as stub area already";
        }
        key "id";
        leaf id {
          type inet:ipv4-address;
        }
        leaf authentication {
          type empty;
        }
        container authentication-key {
          tailf:cli-compact-syntax;
          tailf:cli-sequence-commands;
          leaf auth-type {
            tailf:cli-drop-node-name;
            type uint8;
          }
          leaf auth-key {
            tailf:cli-drop-node-name;
            type string;
          }
        }
        leaf dead-interval {
          type uint32;
        }
        leaf hello-interval {
          type int32;
        }
        list message-digest-key {
          tailf:cli-suppress-mode;
          tailf:cli-delete-when-empty;
          key "id";
          leaf id {
            tailf:cli-suppress-range;
            type uint8;
          }
          container md5 {
            tailf:cli-sequence-commands;
            tailf:cli-compact-syntax;
            leaf auth-type {
              tailf:cli-drop-node-name;
              tailf:cli-optional-in-sequence;
              type uint8;
            }
            leaf auth-key {
              tailf:cli-drop-node-name;
              type string;
            }
          }
        }
        leaf retransmit-interval {
          type uint16;
        }
        leaf transmit-delay {
          type uint16;
        }
      }
    }
  }

  grouping ospf-timers-throttle-spf-grouping {
    container spf {
      tailf:cli-compact-syntax;
      tailf:cli-sequence-commands;
      leaf initial {
        tailf:cli-drop-node-name;
        type uint32;
      }
      leaf minimum {
        tailf:cli-drop-node-name;
        type uint32;
      }
      leaf maximum {
        tailf:cli-drop-node-name;
        type uint32;
      }
    }
  }

  grouping ospf-ospfv3-common-grouping {
    uses ospf-area-grouping;
    container auto-cost {
      tailf:cli-compact-syntax;
      tailf:cli-sequence-commands {
        tailf:cli-reset-siblings;
      }
      leaf reference-bandwidth {
        type uint32;
      }
      leaf rate-unit {
        tailf:cli-drop-node-name;
        type enumeration {
          enum "Gbps";
          enum "Mbps";
        }
      }
    }
    leaf bfd {
      type empty;
    }
    container log-adjacency-changes {
      presence "Log changes in adjacency state";
      leaf detail {
        type empty;
      }
    }
    container max-lsa {
      tailf:cli-sequence-commands {
        tailf:cli-reset-all-siblings;
      }
      tailf:cli-compact-syntax;
      leaf number {
        tailf:cli-drop-node-name;
        type uint32;
      }
      leaf threshold-value {
        tailf:cli-drop-node-name;
        tailf:cli-optional-in-sequence;
        type uint32;
      }
      choice ignore-or-warning {
        case ignore {
          leaf ignore-time {
            tailf:cli-optional-in-sequence;
            type uint32;
          }
          leaf ignore-count {
            tailf:cli-optional-in-sequence;
            type uint32;
          }
          leaf reset-time {
            type uint32;
          }
        }
        case warning {
          leaf warning-only {
            type empty;
          }
        }
      }
    }
    container max-metric {
      tailf:cli-compact-syntax;
      tailf:cli-sequence-commands {
        tailf:cli-reset-siblings;
      }
      leaf router-lsa {
        type empty;
      }
      leaf external-lsa {
        tailf:cli-optional-in-sequence;
        type empty;
      }
      leaf external-lsa-value {
        tailf:cli-drop-node-name;
        tailf:cli-optional-in-sequence;
        type uint32;
      }
      leaf include-stub {
        tailf:cli-optional-in-sequence;
        type empty;
      }
      leaf on-startup {
        tailf:cli-optional-in-sequence;
        type empty;
      }
      leaf on-startup-value {
        tailf:cli-drop-node-name;
        tailf:cli-optional-in-sequence;
        type uint32;
      }
      container wait-for {
        tailf:cli-optional-in-sequence;
        tailf:cli-flatten-container;
        leaf bgp {
          type string;
        }
      }
      leaf summary-lsa {
        type empty;
      }
      leaf summary-lsa-value {
        tailf:cli-drop-node-name;
        type uint32;
      }
    }
    container passive-interface {
      leaf default {
        type empty;
      }
    }
    container timers {
      leaf lsa-arrival {
        type uint32;
      }
      leaf lsa-group-pacing {
        type uint16;
      }
      container throttle {
        container lsa {
          tailf:cli-compact-syntax;
          tailf:cli-sequence-commands;
          leaf start {
            tailf:cli-drop-node-name;
            type uint16;
          }
          leaf hold {
            tailf:cli-drop-node-name;
            type uint16;
          }
          leaf max {
            tailf:cli-drop-node-name;
            type uint16;
          }
        }
        uses ospf-timers-throttle-spf-grouping;
      }
    }
    leaf router-id {
      type inet:ipv4-address;
    }
    container discard-route {
      leaf external {
        type boolean;
      }
      leaf internal {
        type boolean;
      }
    }
    leaf name-lookup {
      type empty;
    }
    leaf graceful-restart {
      type boolean;
    }
    container graceful-restart-config {
      tailf:cli-drop-node-name;
      container graceful-restart {
        leaf grace-period {
          type uint16;
        }
        leaf helper-disable {
          type empty;
        }
      }
    }
    leaf flush-routes {
      type empty;
    }
  }

  grouping ospf-grouping {
    list summary-address {
      tailf:cli-suppress-mode;
      tailf:cli-delete-when-empty;
      key "address";
      leaf address {
        type tailf:ipv4-address-and-prefix-length;
      }
    }
    uses ospf-ospfv3-common-grouping;
    uses common-router-redistribute-grouping;
    leaf default-metric {
      type uint32;
    }
    leaf rfc1583compatibility {
      type empty;
    }
  }

  grouping isis-common-grouping {
    container authentication {
      list key-chain {
        tailf:cli-suppress-mode;
        tailf:cli-delete-when-empty;
        key "type";
        leaf name {
          tailf:cli-drop-node-name;
          tailf:cli-prefix-key;
          type string;
        }
        leaf type {
          type enumeration {
            enum "level-1";
            enum "level-2";
          }
        }
      }
    }
    container authentication-check {
      leaf level-1 {
        type boolean;
      }
      leaf level-2 {
        type boolean;
      }
    }
    list authentication-type {
      tailf:cli-suppress-mode;
      tailf:cli-delete-when-empty;
      key "type";
      leaf auth-format {
        tailf:cli-drop-node-name;
        tailf:cli-prefix-key;
        type enumeration {
          enum "cleartext";
          enum "md5";
        }
      }
      leaf type {
        type enumeration {
          enum "level-1";
          enum "level-2";
        }
      }
    }
    leaf is-type {
      type enumeration {
        enum "level-1";
        enum "level-1-2";
        enum "level-2";
      }
    }
    leaf log-adjacency-changes {
      type empty;
    }
    leaf lsp-mtu {
      type uint16;
    }
    container lsp-gen-interval {
      container level-1 {
        tailf:cli-sequence-commands;
        tailf:cli-compact-syntax;
        uses isis-lsp-gen-interval-grouping;
      }
      container level-2 {
        tailf:cli-sequence-commands;
        tailf:cli-compact-syntax;
        uses isis-lsp-gen-interval-grouping;
      }
    }
    leaf max-lsp-lifetime {
      type uint16;
    }
    leaf net {
      type string;
    }
    uses common-router-redistribute-grouping {
      refine "distance";
    }
    leaf set-attached-bit {
      type boolean;
    }
    container set-overload-bit {
      tailf:cli-compact-syntax;
      tailf:cli-sequence-commands {
        tailf:cli-reset-siblings;
      }
      choice always-or-startup-choice {
        case always-case {
          leaf always {
            type empty;
          }
        }
        case startup-case {
          leaf on-startup {
            type empty;
          }
          leaf elapsed {
            tailf:cli-drop-node-name;
            tailf:cli-optional-in-sequence;
            type uint32;
          }
          container wait-for {
            tailf:cli-flatten-container;
            leaf bgp {
              type asn-type;
            }
          }
        }
      }
      leaf suppress {
        type empty;
      }
      leaf ext-or-int {
        tailf:cli-drop-node-name;
        type enumeration {
          enum "external";
          enum "interlevel";
        }
      }
    }
    container spf-interval {
      container level-1 {
        tailf:cli-compact-syntax;
        tailf:cli-sequence-commands;
        uses isis-spf-interval-grouping;
      }
      container level-2 {
        tailf:cli-compact-syntax;
        tailf:cli-sequence-commands;
        uses isis-spf-interval-grouping;
      }
    }
    container address-family {
      container ipv4 {
        container unicast {
          tailf:cli-add-mode;
          presence "true";
          leaf adjacency-check {
            type boolean;
          }
          uses common-base-redistribute-grouping;
        }
      }
      container ipv6 {
        container unicast {
          tailf:cli-add-mode;
          presence "true";
          leaf adjacency-check {
            type boolean;
          }
          leaf multi-topology {
            type empty;
          }
          uses common-base-redistribute-grouping;
        }
      }
    }
    leaf bfd {
      type empty;
    }
    container metric-style {
      leaf transition {
        type empty;
      }
    }
  }

  grouping eigrp-common-grouping {
    leaf router-id {
      type inet:ipv4-address;
    }
    leaf autonomous-system {
      type uint16;
    }
    leaf log-neighbor-warnings {
      type boolean;
    }
    leaf log-adjacency-changes {
      type boolean;
    }
    container passive-interface {
      leaf default {
        type empty;
      }
    }
    uses common-base-redistribute-grouping;
    container distance {
      tailf:cli-compact-syntax;
      tailf:cli-sequence-commands {
        tailf:cli-reset-siblings;
      }
      leaf internal {
        tailf:cli-drop-node-name;
        type uint8;
      }
      leaf external {
        tailf:cli-drop-node-name;
        type uint8;
      }
    }
    leaf maximum-paths {
      type uint32;
    }
    container default-metric {
      tailf:cli-compact-syntax;
      tailf:cli-sequence-commands {
        tailf:cli-reset-siblings;
      }
      leaf bandwidth {
        tailf:cli-drop-node-name;
        type uint32;
      }
      leaf delay {
        tailf:cli-drop-node-name;
        type uint32;
      }
      leaf reliability {
        tailf:cli-drop-node-name;
        type uint8;
      }
      leaf effective {
        tailf:cli-drop-node-name;
        type uint8;
      }
      leaf max-transmission {
        tailf:cli-drop-node-name;
        type uint16;
      }
    }
    leaf bfd {
      type empty;
    }
    list network {
      tailf:cli-suppress-mode;
      tailf:cli-delete-when-empty;
      key "address";
      leaf address {
        type tailf:ipv4-address-and-prefix-length;
      }
    }
  }

  grouping eigrp-common-af-grouping {
    container address-family {
      container ipv4 {
        container unicast {
          tailf:cli-add-mode;
          uses eigrp-common-grouping {
            refine "network";
          }
        }
      }
      container ipv6 {
        container unicast {
          tailf:cli-add-mode;
          uses eigrp-common-grouping;
        }
      }
    }
  }

  grouping rip-common-af-grouping {
    container address-family {
      container ipv4 {
        container unicast {
          tailf:cli-add-mode;
          uses common-router-redistribute-grouping-rip;
        }
      }
      container ipv6 {
        container unicast {
          tailf:cli-add-mode;
          uses common-router-redistribute-grouping-rip;
        }
      }
    }
  }

  grouping router-bgp-address-family-base-grouping {
    list address-family {
      key "proto type";
      leaf proto {
        type enumeration {
          enum "ipv4";
          enum "ipv6";
          enum "l2vpn";
          enum "vpnv4";
          enum "vpnv6";
          enum "nsap";
          enum "rtfilter";
        }
      }
      leaf type {
        type enumeration {
          enum "unicast";
          enum "multicast";
          enum "mvpn";
          enum "evpn";
          enum "labeled-unicast";
        }
      }
    }
  }

  grouping router-bgp-address-family-grouping {
    uses router-bgp-address-family-base-grouping {
      augment "address-family" {
        uses router-bgp-af-dampening-grouping;
        container nexthop {
          container trigger-delay {
            tailf:cli-compact-syntax;
            tailf:cli-sequence-commands;
            leaf critical {
              type uint32;
            }
            leaf non-critical {
              type uint32;
            }
          }
          leaf route-map {
            type string;
          }
        }
        container additional-paths {
          leaf receive {
            type empty;
          }
          leaf send {
            type empty;
          }
          container selection {
            leaf route-map {
              type string;
            }
          }
          container install {
            leaf backup {
              type empty;
            }
          }
        }
        list aggregate-address {
          tailf:cli-suppress-mode;
          tailf:cli-delete-when-empty;
          tailf:cli-compact-syntax;
          tailf:cli-sequence-commands {
            tailf:cli-reset-siblings;
          }
          key "ip";
          leaf ip {
            type union {
              type tailf:ipv4-address-and-prefix-length;
              type tailf:ipv6-address-and-prefix-length;
            }
          }
          leaf as-set {
            tailf:cli-optional-in-sequence;
            type empty;
          }
          leaf summary-only {
            tailf:cli-optional-in-sequence;
            type empty;
          }
          leaf advertise-map {
            tailf:cli-optional-in-sequence;
            type string;
          }
          leaf suppress-map {
            tailf:cli-optional-in-sequence;
            type string;
          }
          leaf attribute-map {
            type string;
          }
        }
        container advertise {
          leaf l2vpn {
            type enumeration {
              enum "evpn";
            }
          }
        }
        leaf advertise-pip {
          type empty;
        }
        leaf allow-vni-in-ethertag {
          type empty;
        }
        container allocate-label {
          choice label-choice {
            leaf all {
              type empty;
            }
            leaf route-map {
              type string;
            }
          }
        }
        container distance {
          tailf:cli-compact-syntax;
          leaf ebgp {
            tailf:cli-drop-node-name;
            type uint8;
          }
          leaf ibgp {
            tailf:cli-drop-node-name;
            type uint8;
          }
          leaf local {
            tailf:cli-drop-node-name;
            type uint8;
          }
        }
        container maximum-paths {
          leaf ibgp {
            type uint8;
          }
          leaf number {
            tailf:cli-drop-node-name;
            type uint8;
          }
          leaf eibgp {
            type uint8;
          }
          leaf mixed {
            type uint8;
          }
        }
        list network {
          tailf:cli-suppress-mode;
          tailf:cli-delete-when-empty;
          tailf:cli-compact-syntax;
          tailf:cli-sequence-commands;
          key "ip";
          leaf ip {
            type union {
              type inet:ipv4-address;
              type tailf:ipv4-address-and-prefix-length;
              type tailf:ipv6-address-and-prefix-length;
            }
          }
          leaf mask {
            type inet:ipv4-address;
          }
          leaf route-map {
            type string;
          }
        }
        uses common-base-redistribute-grouping;
        leaf default-metric {
          type uint32;
        }
        container retain {
          container route-target {
            choice all-or-map {
              leaf all {
                type empty;
              }
              leaf route-map {
                type string;
              }
            }
          }
        }
        leaf export-gateway-ip {
          type empty;
        }
        leaf prefix-priority {
          type enumeration {
            enum "high";
          }
        }
      }
    }
  }

  grouping template-af-common-grouping {
    leaf default-originate {
      type empty;
    }
    container allowas-in {
      presence "true";
      leaf occurrences {
        tailf:cli-drop-node-name;
        type uint8;
      }
    }
    leaf route-reflector-client {
      type empty;
    }
    leaf soo {
      type string;
    }
    list route-map {
      tailf:cli-suppress-mode;
      tailf:cli-delete-when-empty;
      key "direction";
      leaf name {
        tailf:cli-drop-node-name;
        tailf:cli-prefix-key;
        type string;
      }
      leaf direction {
        type enumeration {
          enum "in";
          enum "out";
        }
      }
    }
    container maximum-prefix {
      tailf:cli-sequence-commands {
        tailf:cli-reset-all-siblings;
      }
      tailf:cli-compact-syntax;
      leaf number {
        tailf:cli-drop-node-name;
        type uint32;
      }
      leaf threshold {
        tailf:cli-drop-node-name;
        tailf:cli-optional-in-sequence;
        type uint32;
      }
      choice restart-or-warning {
        leaf restart {
          type uint16;
        }
        leaf warning-only {
          type empty;
        }
      }
    }
    leaf next-hop-self {
      type empty;
    }
    leaf next-hop-third-party {
      type boolean;
    }
    leaf rewrite-evpn-rt-asn {
      type empty;
    }
    container send-community-attr {
      tailf:cli-drop-node-name;
      leaf send-community {
        type enumeration {
          enum "standard";
          enum "extended";
          enum "both";
        }
      }
    }
    leaf send-community {
      type empty;
    }
    container soft-reconfiguration {
      tailf:cli-compact-syntax;
      tailf:cli-sequence-commands {
        tailf:cli-reset-siblings;
      }
      leaf inbound {
        type empty;
      }
      leaf always {
        type empty;
      }
    }
    list prefix-list {
      tailf:cli-suppress-mode;
      tailf:cli-delete-when-empty;
      key "direction";
      leaf name {
        tailf:cli-drop-node-name;
        tailf:cli-prefix-key;
        type string;
      }
      leaf direction {
        type enumeration {
          enum "in";
          enum "out";
        }
      }
    }
    list filter-list {
      tailf:cli-suppress-mode;
      tailf:cli-delete-when-empty;
      key "direction";
      leaf name {
        tailf:cli-drop-node-name;
        tailf:cli-prefix-key;
        type string;
      }
      leaf direction {
        type enumeration {
          enum "in";
          enum "out";
        }
      }
    }
    leaf disable-peer-as-check {
      type empty;
    }
    container inherit {
      list peer-policy {
        tailf:cli-suppress-mode;
        tailf:cli-delete-when-empty;
        key "name";
        leaf name {
          type string;
        }
        leaf sequence {
          tailf:cli-drop-node-name;
          type uint16;
        }
      }
    }
    container encapsulation {
      leaf mpls {
        type empty;
      }
    }
    container capability {
      container additional-paths {
        choice receive-choice {
          leaf receive {
            type empty;
          }
          container disable-receive {
            tailf:cli-drop-node-name;
            container receive {
              leaf disable {
                type empty;
              }
            }
          }
        }
        choice send-choice {
          leaf send {
            type empty;
          }
          container disable-send {
            tailf:cli-drop-node-name;
            container send {
              leaf disable {
                type empty;
              }
            }
          }
        }
      }
    }
    leaf weight {
      type uint16;
    }
    leaf as-override {
      type empty;
    }
    list advertise-map {
      tailf:cli-suppress-mode;
      tailf:cli-delete-when-empty;
      key "name";
      leaf name {
        type string;
      }
      choice map-choice {
        leaf exist-map {
          type string;
        }
        leaf non-exist-map {
          type string;
        }
      }
    }
    leaf advertisement-interval {
      type uint16;
    }
  }

  grouping template-base-grouping {
    choice local-as-choice {
      leaf local-as {
        type asn-type;
      }
      container local-as-no-prepend {
        tailf:cli-drop-node-name;
        tailf:cli-compact-syntax;
        tailf:cli-sequence-commands {
          tailf:cli-reset-siblings;
        }
        leaf local-as {
          type asn-type;
        }
        leaf no-prepend {
          type empty;
        }
        leaf replace-as {
          type empty;
        }
        leaf dual-as {
          type empty;
        }
      }
    }
    container password {
      tailf:cli-compact-syntax;
      leaf encryption {
        tailf:cli-drop-node-name;
        type enumeration {
          enum "0";
          enum "3";
          enum "7";
        }
      }
      leaf passwd {
        tailf:cli-drop-node-name;
        type string;
      }
    }
    leaf description {
      tailf:cli-multi-value;
      type string;
    }
    leaf ebgp-multihop {
      type uint8;
    }
    container inherit {
      leaf peer {
        type string;
      }
      leaf peer-session {
        type string;
      }
    }
    leaf update-source {
      type string;
    }
    leaf disable-connected-check {
      type empty;
    }
    leaf dynamic-capability {
      type boolean;
    }
    container capability {
      container suppress {
        container four-byte-as {
          tailf:alt-name "4-byte-as";
          presence "true";
          leaf inheritance-disable {
            type empty;
          }
        }
      }
    }
    leaf bfd {
      type empty;
    }
    container bfd-config {
      tailf:cli-drop-node-name;
      container bfd {
        container multihop {
          presence "true";
          container interval {
            tailf:cli-sequence-commands {
              tailf:cli-reset-siblings;
            }
            tailf:cli-compact-syntax;
            leaf tx-interval {
              tailf:cli-drop-node-name;
              type uint16;
            }
            leaf min_rx {
              type uint16;
            }
            leaf multiplier {
              type uint8;
            }
          }
        }
      }
    }
    leaf shutdown {
      type empty;
    }
    container timers {
      tailf:cli-compact-syntax;
      tailf:cli-sequence-commands;
      leaf keepalive {
        tailf:cli-drop-node-name;
        type uint16;
      }
      leaf holdtime {
        tailf:cli-drop-node-name;
        type uint16;
      }
    }
    leaf peer-type {
      type enumeration {
        enum "fabric-border-leaf";
        enum "fabric-external";
      }
    }
    container remove-private-as {
      presence "true";
      tailf:cli-delete-when-empty;
      choice all-or-replace {
        leaf all {
          type empty;
        }
        leaf replace-as {
          type empty;
        }
      }
    }
    leaf log-neighbor-changes {
      type empty;
    }
  }

  grouping template-neighbor-common-grouping {
    uses template-base-grouping;
    list address-family {
      key "proto type";
      leaf proto {
        type enumeration {
          enum "ipv4";
          enum "ipv6";
          enum "l2vpn";
          enum "vpnv4";
          enum "vpnv6";
          enum "nsap";
          enum "rtfilter";
        }
      }
      leaf type {
        type enumeration {
          enum "unicast";
          enum "multicast";
          enum "mvpn";
          enum "evpn";
          enum "labeled-unicast";
        }
      }
      uses template-af-common-grouping;
      container import {
        container vpn {
          container unicast {
            leaf reoriginate {
              type empty;
            }
            leaf route-map {
              type string;
            }
          }
        }
        container l2vpn {
          container evpn {
            tailf:cli-compact-syntax;
            tailf:cli-delete-when-empty;
            presence "true";
            leaf reoriginate {
              type empty;
            }
            leaf route-map {
              type string;
            }
          }
        }
      }
      container advertise {
        leaf local-labeled-route {
          type boolean;
        }
      }
    }
    choice egress-eng-choice {
      leaf egress-engineering {
        type empty;
      }
      container egress-engineering-peerset {
        tailf:cli-drop-node-name;
        container egress-engineering {
          leaf peer-set {
            type string;
          }
        }
      }
    }
    leaf dont-capability-negotiate {
      type empty;
    }
  }

  grouping router-bgp-grouping {
    uses router-bgp-address-family-grouping;
    leaf log-neighbor-changes {
      type empty;
    }
    leaf router-id {
      type inet:ipv4-address;
    }
    container rd {
      container dual {
        leaf id {
          type uint16;
        }
      }
    }
    leaf cluster-id {
      type union {
        type uint32;
        type inet:ipv4-address;
      }
    }
    list neighbor {
      key "id";
      leaf id {
        type union {
          type inet:ipv4-address;
          type inet:ipv6-address;
          type tailf:ipv4-address-and-prefix-length;
          type tailf:ipv6-address-and-prefix-length;
          type string;
        }
      }
      container remote-as {
        tailf:cli-compact-syntax;
        tailf:cli-flatten-container;
        tailf:cli-hide-in-submode;
        choice remote-as-choice {
          leaf as-number {
            tailf:cli-drop-node-name;
            tailf:cli-hide-in-submode;
            type string;
          }
          leaf route-map {
            tailf:cli-hide-in-submode;
            type string;
          }
        }
      }
      container inner-remote-as {
        tailf:cli-drop-node-name;
        leaf remote-as {
          type asn-type;
        }
      }
      leaf rewrite-evpn-rt-asn {
        type empty;
      }
      uses template-neighbor-common-grouping;
      container af-linkstate {
        tailf:cli-drop-node-name;
        container address-family {
          container link-state {
            tailf:cli-add-mode;
            presence "true";
            leaf allowas-in {
              type uint8;
            }
          }
        }
      }
      container transport {
        container connection-mode {
          leaf passive {
            type empty;
          }
        }
      }
    }
    leaf suppress-fib-pending {
      type empty;
    }
    container timers {
      container bgp {
        tailf:cli-compact-syntax;
        tailf:cli-sequence-commands;
        leaf keepalive {
          tailf:cli-drop-node-name;
          type uint16;
        }
        leaf holdtime {
          tailf:cli-drop-node-name;
          type uint16;
        }
      }
      leaf bestpath-limit {
        type uint16;
      }
    }
    leaf graceful-restart {
      type boolean;
    }
    container graceful-restart-config {
      tailf:cli-drop-node-name;
      container graceful-restart {
        leaf restart-time {
          type uint16;
        }
        leaf stalepath-time {
          type uint16;
        }
      }
    }
    container bestpath {
      leaf always-compare-med {
        type empty;
      }
      container as-path {
        leaf multipath-relax {
          type empty;
        }
        leaf ignore {
          type empty;
        }
      }
      leaf compare-neighborid {
        type empty;
      }
      leaf compare-routerid {
        type empty;
      }
      container cost-community {
        leaf ignore {
          type empty;
        }
      }
      container igp-metric {
        leaf ignore {
          type empty;
        }
      }
      container med {
        leaf confed {
          type empty;
        }
        leaf missing-as-worst {
          type empty;
        }
        leaf non-deterministic {
          type empty;
        }
      }
    }
    container neighbor-down {
      leaf fib-accelerate {
        type empty;
      }
    }
  }

  grouping router-bgp-af-dampening-grouping {
    choice dampening-choice {
      leaf dampening {
        type empty;
      }
      container rm-dampening {
        tailf:cli-drop-node-name;
        container dampening {
          leaf route-map {
            type string;
          }
        }
      }
      container spec-dampening {
        tailf:cli-drop-node-name;
        container dampening {
          tailf:cli-compact-syntax;
          tailf:cli-sequence-commands {
            tailf:cli-reset-siblings;
          }
          leaf decay {
            tailf:cli-drop-node-name;
            type uint8;
          }
          leaf reuse {
            tailf:cli-drop-node-name;
            type uint16;
          }
          leaf suppress {
            tailf:cli-drop-node-name;
            type uint16;
          }
          leaf max-suppress {
            tailf:cli-drop-node-name;
            type uint8;
          }
        }
      }
    }
  }

  grouping ip-route-options-grouping {
    leaf track {
      tailf:cli-optional-in-sequence;
      type uint16;
    }
    leaf name {
      tailf:cli-optional-in-sequence;
      type string;
    }
    leaf tag {
      tailf:cli-optional-in-sequence;
      type uint32;
    }
    leaf preference {
      tailf:cli-drop-node-name;
      type uint8;
    }
  }

  grouping ip-access-packet-match-grouping {
    choice match-type-choice {
      case packet-match {
        leaf packet-match {
          tailf:cli-drop-node-name;
          type enumeration {
            enum "eq";
            enum "gt";
            enum "lt";
            enum "neq";
            enum "range";
          }
        }
        leaf value {
          tailf:cli-drop-node-name;
          type protocol-port-type;
        }
        leaf end-value {
          tailf:cli-drop-node-name;
          type protocol-port-type;
        }
      }
      case group-match {
        leaf portgroup {
          type string;
        }
      }
    }
  }

  grouping ip-access-list-option-grouping {
    container common-packet-match {
      tailf:cli-drop-node-name;
      tailf:cli-flatten-container;
      tailf:cli-optional-in-sequence;
      tailf:cli-sequence-commands;
      tailf:cli-compact-syntax;
      uses ip-access-packet-match-grouping;
    }
    leaf urg {
      tailf:cli-optional-in-sequence;
      type empty;
    }
    leaf ack {
      tailf:cli-optional-in-sequence;
      type empty;
    }
    leaf psh {
      tailf:cli-optional-in-sequence;
      type empty;
    }
    leaf rst {
      tailf:cli-optional-in-sequence;
      type empty;
    }
    leaf syn {
      tailf:cli-optional-in-sequence;
      type empty;
    }
    leaf fin {
      tailf:cli-optional-in-sequence;
      type empty;
    }
    leaf established {
      tailf:cli-optional-in-sequence;
      type empty;
    }
    choice dscp-or-precedence {
      leaf dscp {
        tailf:cli-optional-in-sequence;
        type dscp-value-type;
      }
      leaf precedence {
        tailf:cli-optional-in-sequence;
        type precedence-type;
      }
    }
    leaf fragments {
      tailf:cli-optional-in-sequence;
      type empty;
    }
    leaf time-range {
      tailf:cli-optional-in-sequence;
      type string;
    }
    container packet-length {
      tailf:cli-optional-in-sequence;
      tailf:cli-flatten-container;
      tailf:cli-sequence-commands;
      tailf:cli-compact-syntax;
      leaf op {
        tailf:cli-drop-node-name;
        type enumeration {
          enum "eq";
          enum "gt";
          enum "lt";
          enum "neq";
          enum "range";
        }
      }
      leaf value {
        tailf:cli-drop-node-name;
        type uint16;
      }
      leaf value-high {
        tailf:cli-drop-node-name;
        type uint16;
      }
    }
    leaf log {
      tailf:cli-optional-in-sequence;
      type empty;
    }
    choice capture-or-redirect {
      container capture {
        tailf:cli-flatten-container;
        tailf:cli-compact-syntax;
        leaf session {
          type uint8;
        }
      }
      container redirect-config {
        tailf:cli-drop-node-name;
        tailf:cli-sequence-commands {
          tailf:cli-reset-siblings;
        }
        tailf:cli-compact-syntax;
        tailf:cli-flatten-container;
        leaf redirect {
          type empty;
        }
        leaf redirect-interfaces {
          tailf:cli-drop-node-name;
          type string;
        }
      }
    }
  }

  grouping ip-access-list-grouping {
    leaf protocol {
      tailf:cli-drop-node-name;
      type union {
        type uint8;
        type enumeration {
          enum "ahp" {
            value 51;
          }
          enum "eigrp" {
            value 88;
          }
          enum "esp" {
            value 50;
          }
          enum "gre" {
            value 47;
          }
          enum "icmp" {
            value 1;
          }
          enum "igmp" {
            value 2;
          }
          enum "ip" {
            value 0;
          }
          enum "nos" {
            value 94;
          }
          enum "ospf" {
            value 89;
          }
          enum "pcp" {
            value 108;
          }
          enum "pim" {
            value 103;
          }
          enum "tcp" {
            value 6;
          }
          enum "udp" {
            value 17;
          }
        }
      }
    }
    container source {
      tailf:cli-drop-node-name;
      tailf:cli-flatten-container;
      tailf:cli-compact-syntax;
      tailf:cli-sequence-commands;
      choice source-choice {
        leaf host {
          type inet:ipv4-address;
        }
        leaf any {
          type empty;
        }
        leaf address-and-prefix {
          tailf:cli-drop-node-name;
          type tailf:ipv4-address-and-prefix-length;
        }
        leaf address {
          tailf:cli-drop-node-name;
          type inet:ipv4-address;
        }
        leaf addrgroup {
          type string;
        }
      }
      leaf source-mask {
        tailf:cli-drop-node-name;
        type inet:ipv4-address;
      }
    }
    container packet-match-source {
      tailf:cli-drop-node-name;
      tailf:cli-flatten-container;
      tailf:cli-optional-in-sequence;
      tailf:cli-sequence-commands;
      tailf:cli-compact-syntax;
      uses ip-access-packet-match-grouping;
    }
    choice destination-choice {
      leaf host {
        type inet:ipv4-address;
      }
      leaf any {
        type empty;
      }
      leaf address-and-prefix {
        tailf:cli-drop-node-name;
        type tailf:ipv4-address-and-prefix-length;
      }
      leaf address {
        tailf:cli-drop-node-name;
        type inet:ipv4-address;
      }
      leaf addrgroup {
        type string;
      }
    }
    leaf dest-mask {
      tailf:cli-drop-node-name;
      type inet:ipv4-address;
    }
    leaf icmp-message-match {
      tailf:cli-drop-node-name;
      tailf:cli-optional-in-sequence;
      type union {
        type uint8;
        type enumeration {
          enum "echo-reply" {
            value 0;
          }
          enum "echo" {
            value 8;
          }
          enum "ttl-exceeded" {
            value 11;
          }
          enum "time-exceeded";
          enum "port-unreachable" {
            value 3;
          }
          enum "host-unreachable";
          enum "unreachable";
          enum "packet-too-big";
          enum "hop-limit";
          enum "next-header";
          enum "parameter-option";
          enum "parameter-problem";
          enum "protocol-unreachable";
          enum "administratively-prohibited";
          enum "alternate-address";
          enum "conversion-error";
          enum "dod-host-prohibited";
          enum "dod-net-prohibited";
          enum "general-parameter-problem";
          enum "host-isolated";
          enum "host-precedence-unreachable";
          enum "host-redirect";
          enum "host-tos-redirect";
          enum "host-tos-unreachable";
          enum "host-unknown";
          enum "information-reply";
          enum "information-request";
          enum "mask-reply";
          enum "mask-request";
          enum "mobile-redirect";
          enum "net-redirect";
          enum "net-tos-redirect";
          enum "net-tos-unreachable";
          enum "net-unreachable";
          enum "network-unknown";
          enum "no-room-for-option";
          enum "option-missing";
          enum "precedence-unreachable";
          enum "reassembly-timeout";
          enum "router-advertisement";
          enum "router-solicitation";
          enum "traceroute";
          enum "source-quench";
          enum "source-route-failed";
        }
      }
    }
    leaf icmp-message-code {
      tailf:cli-drop-node-name;
      tailf:cli-optional-in-sequence;
      type uint8;
    }
    leaf igmp-message-match {
      tailf:cli-drop-node-name;
      tailf:cli-optional-in-sequence;
      type enumeration {
        enum "dvmrp";
        enum "host-query";
        enum "host-report";
        enum "pim";
      }
    }
    uses ip-access-list-option-grouping;
  }

  grouping ipv6-access-list-grouping {
    leaf protocol {
      tailf:cli-drop-node-name;
      type union {
        type uint8;
        type enumeration {
          enum "ahp" {
            value 51;
          }
          enum "eigrp" {
            value 88;
          }
          enum "esp" {
            value 50;
          }
          enum "gre" {
            value 47;
          }
          enum "icmp" {
            value 58;
          }
          enum "ipv6" {
            value 41;
          }
          enum "sctp" {
            value 132;
          }
          enum "nos" {
            value 94;
          }
          enum "ospf" {
            value 89;
          }
          enum "pcp" {
            value 108;
          }
          enum "pim" {
            value 103;
          }
          enum "tcp" {
            value 6;
          }
          enum "udp" {
            value 17;
          }
          enum "ip";
        }
      }
    }
    container source {
      tailf:cli-drop-node-name;
      tailf:cli-flatten-container;
      tailf:cli-compact-syntax;
      tailf:cli-sequence-commands;
      choice source-choice {
        leaf host {
          type inet:ipv6-address;
        }
        leaf any {
          type empty;
        }
        leaf address-and-prefix {
          tailf:cli-drop-node-name;
          type tailf:ipv6-address-and-prefix-length;
        }
        leaf address {
          tailf:cli-drop-node-name;
          type inet:ipv6-address;
        }
        leaf addrgroup {
          type string;
        }
      }
      leaf source-mask {
        tailf:cli-drop-node-name;
        type inet:ipv6-address;
      }
    }
    container packet-match-source {
      tailf:cli-drop-node-name;
      tailf:cli-flatten-container;
      tailf:cli-optional-in-sequence;
      tailf:cli-sequence-commands;
      tailf:cli-compact-syntax;
      uses ip-access-packet-match-grouping;
    }
    choice destination-choice {
      leaf host {
        type inet:ipv6-address;
      }
      leaf any {
        type empty;
      }
      leaf address-and-prefix {
        tailf:cli-drop-node-name;
        type tailf:ipv6-address-and-prefix-length;
      }
      leaf address {
        tailf:cli-drop-node-name;
        type inet:ipv6-address;
      }
      leaf addrgroup {
        type string;
      }
    }
    leaf dest-mask {
      tailf:cli-drop-node-name;
      type inet:ipv6-address;
    }
    leaf icmpv6-message-type {
      tailf:cli-drop-node-name;
      tailf:cli-optional-in-sequence;
      type enumeration {
        enum "echo-request" {
          value 128;
        }
        enum "echo-reply" {
          value 129;
        }
        enum "router-solicitation" {
          value 133;
        }
        enum "router-advertisement" {
          value 134;
        }
        enum "nd-ns" {
          value 135;
        }
        enum "nd-na" {
          value 136;
        }
        enum "mld-query" {
          value 130;
        }
        enum "mld-reduction";
        enum "mld-report" {
          value 131;
        }
        enum "mldv2";
        enum "hop-limit";
        enum "next-header";
        enum "packet-too-big";
        enum "parameter-option";
        enum "parameter-problem";
        enum "no-route";
        enum "port-unreachable";
        enum "unreachable";
        enum "router-renumbering";
        enum "time-exceeded";
        enum "header";
        enum "destination-unreachable";
        enum "renum-command";
        enum "renum-result";
        enum "renum-seq-number";
      }
    }
    uses ip-access-list-option-grouping;
  }

  grouping ip-access-list-common-grouping {
    leaf fragments {
      type enumeration {
        enum "deny-all";
        enum "permit-all";
      }
    }
    container statistics {
      leaf per-entry {
        type empty;
      }
    }
  }

  grouping ip-grouping {
    list domain-list {
      tailf:cli-suppress-mode;
      key "name";
      leaf name {
        type string;
      }
    }
    leaf domain-name {
      type string;
    }
    container name-server {
      tailf:cli-compact-syntax;
      leaf-list servers {
        tailf:cli-drop-node-name;
        tailf:cli-flat-list-syntax;
        ordered-by user;
        type union {
          type inet:ipv4-address;
          type inet:ipv6-address;
        }
      }
    }
    container name-server-vrf {
      tailf:cli-drop-node-name;
      list name-server {
        tailf:cli-suppress-mode;
        tailf:cli-compact-syntax;
        key "use-vrf";
        leaf use-vrf {
          tailf:cli-expose-key-name;
          type string;
        }
        leaf-list servers {
          tailf:cli-drop-node-name;
          tailf:cli-flat-list-syntax;
          ordered-by user;
          type union {
            type inet:ipv4-address;
            type inet:ipv6-address;
          }
        }
      }
    }
    container route {
      container static {
        container bfd {
          list port-channel {
            tailf:cli-suppress-mode;
            tailf:cli-delete-when-empty;
            tailf:cli-allow-join-with-key;
            key "id";
            leaf id {
              type string;
            }
            leaf-list next-hop {
              tailf:cli-drop-node-name;
              type inet:ipv4-address;
            }
          }
          list Vlan {
            tailf:cli-suppress-mode;
            tailf:cli-delete-when-empty;
            tailf:cli-allow-join-with-key;
            key "id";
            leaf id {
              type uint16;
            }
            leaf-list next-hop {
              tailf:cli-drop-node-name;
              type inet:ipv4-address;
            }
          }
          list Ethernet {
            tailf:cli-suppress-mode;
            tailf:cli-delete-when-empty;
            tailf:cli-allow-join-with-key;
            key "name";
            leaf name {
              type string;
            }
            leaf-list next-hop {
              tailf:cli-drop-node-name;
              type inet:ipv4-address;
            }
          }
        }
      }
      list ip-route-list {
        tailf:cli-drop-node-name;
        tailf:cli-suppress-mode;
        tailf:cli-delete-when-empty;
        tailf:cli-compact-syntax;
        tailf:cli-sequence-commands {
          tailf:cli-reset-all-siblings;
        }
        key "prefix-mask next-hop";
        leaf prefix-mask {
          type tailf:ipv4-address-and-prefix-length;
        }
        leaf next-hop {
          type union {
            type inet:ipv4-address;
            type tailf:ipv4-address-and-prefix-length;
            type enumeration {
              enum "Null0";
            }
            type string;
          }
        }
        uses ip-route-options-grouping;
      }
      list ip-route-interface-list {
        tailf:cli-drop-node-name;
        tailf:cli-suppress-mode;
        tailf:cli-delete-when-empty;
        tailf:cli-compact-syntax;
        tailf:cli-sequence-commands {
          tailf:cli-reset-all-siblings;
        }
        key "prefix-mask interface next-hop";
        leaf prefix-mask {
          type tailf:ipv4-address-and-prefix-length;
        }
        leaf interface {
          type string;
        }
        leaf next-hop {
          type union {
            type inet:ipv4-address;
            type tailf:ipv4-address-and-prefix-length;
          }
        }
        uses ip-route-options-grouping;
      }
      list ip-route-vrf-list {
        tailf:cli-drop-node-name;
        tailf:cli-suppress-mode;
        tailf:cli-delete-when-empty;
        tailf:cli-compact-syntax;
        tailf:cli-sequence-commands {
          tailf:cli-reset-all-siblings;
        }
        key "prefix-mask next-hop vrf";
        leaf prefix-mask {
          type tailf:ipv4-address-and-prefix-length;
        }
        leaf next-hop {
          type union {
            type inet:ipv4-address;
            type tailf:ipv4-address-and-prefix-length;
            type enumeration {
              enum "Null0";
            }
            type string;
          }
        }
        leaf vrf {
          tailf:cli-expose-key-name;
          type string;
        }
        uses ip-route-options-grouping;
      }
      list ip-route-interface-vrf-list {
        tailf:cli-drop-node-name;
        tailf:cli-suppress-mode;
        tailf:cli-delete-when-empty;
        tailf:cli-compact-syntax;
        tailf:cli-sequence-commands {
          tailf:cli-reset-all-siblings;
        }
        key "prefix-mask interface next-hop vrf";
        leaf prefix-mask {
          type tailf:ipv4-address-and-prefix-length;
        }
        leaf interface {
          type string;
        }
        leaf next-hop {
          type union {
            type inet:ipv4-address;
            type tailf:ipv4-address-and-prefix-length;
          }
        }
        leaf vrf {
          tailf:cli-expose-key-name;
          type string;
        }
        uses ip-route-options-grouping;
      }
    }
    container mroute {
      list ip-mroute-list {
        tailf:cli-drop-node-name;
        tailf:cli-suppress-mode;
        tailf:cli-delete-when-empty;
        tailf:cli-compact-syntax;
        tailf:cli-sequence-commands {
          tailf:cli-reset-all-siblings;
        }
        key "prefix-mask next-hop";
        leaf prefix-mask {
          type tailf:ipv4-address-and-prefix-length;
        }
        leaf next-hop {
          type union {
            type inet:ipv4-address;
            type tailf:ipv4-address-and-prefix-length;
          }
        }
      }
    }
    container multicast {
      container multipath {
        choice hash-or-disable-choice {
          leaf legacy {
            type empty;
          }
          container s-g-hash {
            leaf next-hop-based {
              type empty;
            }
          }
          leaf none {
            type empty;
          }
        }
        leaf nbm {
          type empty;
        }
        leaf resilient {
          type empty;
        }
      }
      container multipath-enable {
        tailf:cli-drop-node-name;
        leaf multipath {
          type empty;
        }
      }
    }
    container icmp-errors {
      leaf source-interface {
        type string;
      }
    }
    uses ip-pim-grouping;
  }

  grouping iface-choice-grouping {
    choice iface-choice {
      leaf Ethernet {
        tailf:cli-allow-join-with-value;
        type string;
      }
      leaf loopback {
        tailf:cli-allow-join-with-value;
        type uint16;
      }
      leaf port-channel {
        tailf:cli-allow-join-with-value;
        type string;
      }
    }
  }

  grouping rp-candidate-grouping {
    container rp-candidate {
      tailf:cli-sequence-commands {
        tailf:cli-reset-siblings;
      }
      tailf:cli-compact-syntax;
      uses iface-choice-grouping;
      choice policy-choice {
        leaf group-list {
          type tailf:ipv4-address-and-prefix-length;
        }
        leaf prefix-list {
          type string;
        }
        leaf route-map {
          type string;
        }
      }
    }
    leaf rp-candidate-policy {
      type string;
    }
  }

  grouping forward-listen-grouping {
    choice fwd-lstn-choice {
      leaf forward {
        type empty;
      }
      leaf listen {
        type empty;
      }
      container forward-and-listen {
        tailf:cli-drop-node-name;
        tailf:cli-sequence-commands;
        tailf:cli-compact-syntax;
        leaf forward {
          type empty;
        }
        leaf listen {
          type empty;
        }
      }
    }
  }

  grouping ip-pim-grouping {
    container pim {
      list anycast-rp {
        tailf:cli-suppress-mode;
        key "address rp";
        leaf address {
          type inet:ipv4-address;
        }
        leaf rp {
          type inet:ipv4-address;
        }
      }
      container auto-rp {
        uses forward-listen-grouping;
        container mapping-agent {
          tailf:cli-sequence-commands {
            tailf:cli-reset-siblings;
          }
          tailf:cli-compact-syntax;
          uses iface-choice-grouping;
          leaf scope {
            type uint8;
          }
        }
        leaf mapping-agent-policy {
          type string;
        }
        uses rp-candidate-grouping;
      }
      leaf bidir-rp-limit {
        type uint8;
      }
      container bsr {
        container bsr-candidate {
          tailf:cli-sequence-commands {
            tailf:cli-reset-siblings;
          }
          tailf:cli-compact-syntax;
          uses iface-choice-grouping;
          leaf hash-len {
            type uint8;
          }
          leaf priority {
            type uint8;
          }
          leaf interval {
            type uint16;
          }
        }
        leaf bsr-policy {
          type string;
        }
        uses forward-listen-grouping;
        uses rp-candidate-grouping;
      }
      container bsr-candidate;
      leaf bfd {
        type empty;
      }
      leaf flush-routes {
        type empty;
      }
      leaf log-neighbor-changes {
        type empty;
      }
      leaf pre-build-spt {
        type empty;
      }
      choice register-policy-choice {
        leaf register-policy {
          type string;
        }
        container register-policy-prefix-list {
          tailf:cli-drop-node-name;
          container register-policy {
            leaf prefix-list {
              type string;
            }
          }
        }
      }
      leaf register-rate-limit {
        type uint16;
      }
      leaf register-until-stop {
        type empty;
      }
      leaf register-source {
        type string;
      }
      list rp-address {
        tailf:cli-suppress-mode;
        tailf:cli-delete-when-empty;
        key "ip-address";
        leaf ip-address {
          type inet:ipv4-address;
        }
        list group-list {
          tailf:cli-suppress-mode;
          tailf:cli-delete-when-empty;
          tailf:cli-compact-syntax;
          tailf:cli-sequence-commands;
          key "group-range-prefix";
          leaf group-range-prefix {
            type tailf:ipv4-address-and-prefix-length;
          }
          leaf bidir {
            tailf:cli-optional-in-sequence;
            type empty;
          }
          leaf override {
            type empty;
          }
        }
        container prefix-list {
          tailf:cli-compact-syntax;
          tailf:cli-sequence-commands;
          leaf prefix-list-name {
            tailf:cli-drop-node-name;
            type string;
          }
          leaf bidir {
            tailf:cli-optional-in-sequence;
            type empty;
          }
          leaf override {
            type empty;
          }
        }
        container route-map {
          tailf:cli-compact-syntax;
          tailf:cli-sequence-commands;
          leaf route-map-name {
            tailf:cli-drop-node-name;
            type string;
          }
          leaf bidir {
            tailf:cli-optional-in-sequence;
            type empty;
          }
          leaf override {
            type empty;
          }
        }
      }
      container ssm {
        choice ssm-choice {
          leaf prefix-list {
            type string;
          }
          container range {
            choice range-choice {
              leaf-list list-of-group {
                tailf:cli-drop-node-name;
                tailf:cli-flat-list-syntax;
                type tailf:ipv4-address-and-prefix-length;
              }
              leaf none {
                type empty;
              }
            }
          }
          leaf route-map {
            type string;
          }
        }
      }
      leaf state-limit {
        type uint32;
      }
    }
  }

  grouping ipv6-grouping {
    container route {
      list ipv6-route-interface-list {
        tailf:cli-drop-node-name;
        tailf:cli-suppress-mode;
        tailf:cli-delete-when-empty;
        tailf:cli-compact-syntax;
        tailf:cli-sequence-commands {
          tailf:cli-reset-all-siblings;
        }
        key "prefix-mask interface next-hop";
        leaf prefix-mask {
          type tailf:ipv6-address-and-prefix-length;
        }
        leaf interface {
          type string;
        }
        leaf next-hop {
          type union {
            type inet:ipv6-address;
            type tailf:ipv6-address-and-prefix-length;
            type enumeration {
              enum "Null0";
            }
          }
        }
        uses ip-route-options-grouping;
      }
      list ipv6-route-list {
        tailf:cli-drop-node-name;
        tailf:cli-suppress-mode;
        tailf:cli-delete-when-empty;
        tailf:cli-compact-syntax;
        tailf:cli-sequence-commands {
          tailf:cli-reset-all-siblings;
        }
        key "prefix-mask next-hop";
        leaf prefix-mask {
          type tailf:ipv6-address-and-prefix-length;
        }
        leaf next-hop {
          type union {
            type inet:ipv6-address;
            type tailf:ipv6-address-and-prefix-length;
            type enumeration {
              enum "Null0";
            }
          }
        }
        uses ip-route-options-grouping;
      }
      list ipv6-route-vrf-list {
        tailf:cli-drop-node-name;
        tailf:cli-suppress-mode;
        tailf:cli-delete-when-empty;
        tailf:cli-compact-syntax;
        tailf:cli-sequence-commands {
          tailf:cli-reset-all-siblings;
        }
        key "prefix-mask next-hop vrf";
        leaf prefix-mask {
          type tailf:ipv6-address-and-prefix-length;
        }
        leaf interface {
          tailf:cli-optional-in-sequence;
          tailf:cli-drop-node-name;
          tailf:cli-prefix-key {
            tailf:cli-before-key "2";
          }
          type string;
        }
        leaf next-hop {
          type union {
            type inet:ipv6-address;
            type tailf:ipv6-address-and-prefix-length;
            type enumeration {
              enum "Null0";
            }
          }
        }
        leaf vrf {
          tailf:cli-expose-key-name;
          type string;
        }
        uses ip-route-options-grouping;
      }
      container static {
        container bfd {
          list Vlan {
            tailf:cli-suppress-mode;
            tailf:cli-delete-when-empty;
            tailf:cli-allow-join-with-key;
            key "id next-hop";
            leaf id {
              type uint16;
            }
            leaf next-hop {
              type inet:ipv6-address;
            }
          }
          list Ethernet {
            tailf:cli-suppress-mode;
            tailf:cli-allow-join-with-key;
            key "name next-hop";
            leaf name {
              type string;
            }
            leaf next-hop {
              type inet:ipv6-address;
            }
          }
          list port-channel {
            tailf:cli-suppress-mode;
            tailf:cli-allow-join-with-key;
            key "id next-hop";
            leaf id {
              type string;
            }
            leaf next-hop {
              type inet:ipv6-address;
            }
          }
        }
      }
    }
    container pim {
      container ssm {
        choice rm-or-range {
          container range-none {
            tailf:cli-drop-node-name;
            container range {
              leaf none {
                type empty;
              }
            }
          }
          leaf-list range {
            tailf:cli-flat-list-syntax;
            type inet:ipv6-prefix;
          }
          leaf route-map {
            type string;
          }
        }
      }
    }
  }

  grouping line-access-class-grouping {
    list access-class {
      tailf:cli-suppress-mode;
      tailf:cli-delete-when-empty;
      key "direction";
      leaf name {
        tailf:cli-drop-node-name;
        tailf:cli-prefix-key;
        type string;
      }
      leaf direction {
        type enumeration {
          enum "in";
          enum "out";
        }
      }
    }
  }

  grouping line-grouping {
    leaf exec-timeout {
      type uint32;
    }
    uses line-access-class-grouping;
    container ipv6 {
      uses line-access-class-grouping;
    }
    container privilege {
      leaf level {
        type uint8;
      }
    }
  }

  grouping vdc-grouping {
    container limit-resource {
      leaf-list module-type {
        tailf:cli-flat-list-syntax;
        type module-type;
      }
      container anycast_bundleid {
        tailf:cli-compact-syntax;
        leaf minimum {
          type enumeration {
            enum "0";
          }
        }
        leaf maximum {
          type uint16;
        }
      }
      container vlan {
        tailf:cli-compact-syntax;
        leaf minimum {
          type uint16;
        }
        leaf maximum {
          type uint16;
        }
      }
      container monitor-session {
        tailf:cli-compact-syntax;
        leaf minimum {
          type uint16;
        }
        leaf maximum {
          type uint16;
        }
      }
      container monitor-rbs-filter {
        tailf:cli-compact-syntax;
        leaf minimum {
          type uint16;
        }
        leaf maximum {
          type uint16;
        }
      }
      container monitor-rbs-product {
        tailf:cli-compact-syntax;
        leaf minimum {
          type uint16;
        }
        leaf maximum {
          type uint16;
        }
      }
      container monitor-session-erspan-dst {
        tailf:cli-compact-syntax;
        leaf minimum {
          type uint16;
        }
        leaf maximum {
          type uint16;
        }
      }
      container monitor-session-extended {
        tailf:cli-compact-syntax;
        leaf minimum {
          type uint16;
        }
        leaf maximum {
          type uint16;
        }
      }
      container monitor-session-inband-src {
        tailf:cli-compact-syntax;
        leaf minimum {
          type uint16;
        }
        leaf maximum {
          type uint16;
        }
      }
      container monitor-session-mx-exception-src {
        tailf:cli-compact-syntax;
        leaf minimum {
          type uint16;
        }
        leaf maximum {
          type uint16;
        }
      }
      container vrf {
        tailf:cli-compact-syntax;
        leaf minimum {
          type uint16;
        }
        leaf maximum {
          type uint16;
        }
      }
      container vrf-session {
        tailf:cli-compact-syntax;
        leaf minimum {
          type uint16;
        }
        leaf maximum {
          type uint16;
        }
      }
      container port-channel {
        tailf:cli-compact-syntax;
        leaf minimum {
          type uint16;
        }
        leaf maximum {
          type uint16;
        }
      }
      container u4route-mem {
        tailf:cli-compact-syntax;
        leaf minimum {
          type uint16;
        }
        leaf maximum {
          type uint16;
        }
      }
      container u6route-mem {
        tailf:cli-compact-syntax;
        leaf minimum {
          type uint16;
        }
        leaf maximum {
          type uint16;
        }
      }
      container m4route-mem {
        tailf:cli-compact-syntax;
        leaf minimum {
          type uint16;
        }
        leaf maximum {
          type uint16;
        }
      }
      container m6route-mem {
        tailf:cli-compact-syntax;
        leaf minimum {
          type uint16;
        }
        leaf maximum {
          type uint16;
        }
      }
      container vni_bd {
        tailf:cli-compact-syntax;
        leaf minimum {
          type uint16;
        }
        leaf maximum {
          type uint16;
        }
      }
    }
  }

  grouping aaa-group-local-grouping {
    leaf group {
      type string;
    }
    leaf local {
      type boolean;
    }
  }

  grouping interface-eth-and-mgmt-grouping {
    container lldp {
      leaf transmit {
        type boolean;
      }
      leaf receive {
        type boolean;
      }
      container tlv-set {
        leaf management-address {
          type union {
            type inet:ipv4-address;
            type inet:ipv6-address;
          }
        }
        choice vlan-or-id {
          leaf vlan {
            type empty;
          }
          container vlan-id {
            tailf:cli-drop-node-name;
            leaf vlan {
              type uint16;
            }
          }
        }
      }
    }
    container cdp {
      leaf enable {
        type boolean;
      }
    }
    uses interface-l2port-common-grouping;
  }

  grouping class-map-match-exception-ip-grouping {
    container icmp {
      leaf redirect {
        type empty;
      }
      leaf unreachable {
        type empty;
      }
    }
    container multicast {
      leaf directly-connected-sources {
        type empty;
      }
      leaf rpf-failure {
        type empty;
      }
    }
    leaf municast {
      type empty;
    }
    leaf option {
      type empty;
    }
    container unicast {
      leaf rpf-failure {
        type empty;
      }
    }
  }

  grouping feature-set-grouping {
    leaf fabric {
      type empty;
    }
    leaf fabricpath {
      type empty;
    }
    leaf fcoe {
      type empty;
    }
    leaf fex {
      type empty;
    }
    leaf mpls {
      type empty;
    }
    leaf virtualization {
      type empty;
    }
  }

  grouping vlan-bd-config-grouping {
    container ip {
      container igmp {
        container snooping-disable {
          tailf:cli-drop-node-name;
          leaf snooping {
            type boolean;
          }
        }
        container snooping {
          list access-group {
            tailf:cli-suppress-mode;
            tailf:cli-delete-when-empty;
            tailf:cli-compact-syntax;
            tailf:cli-sequence-commands;
            key "interface";
            leaf interface {
              tailf:cli-expose-key-name;
              type string;
            }
            choice prefix-key-choice {
              leaf prefix-list {
                tailf:cli-prefix-key;
                type string;
              }
              leaf route-map {
                tailf:cli-prefix-key;
                type string;
              }
            }
          }
          container access-group-leaf {
            tailf:cli-drop-node-name;
            leaf access-group {
              tailf:alt-name "access-group";
              type string;
            }
          }
          leaf explicit-tracking {
            type boolean;
          }
          leaf fast-leave {
            type empty;
          }
          leaf last-member-query-interval {
            type uint8;
          }
          leaf link-local-groups-suppression {
            type boolean;
          }
          container mrouter {
            container interface {
              list Ethernet {
                tailf:cli-allow-join-with-key;
                tailf:cli-suppress-mode;
                tailf:cli-delete-when-empty;
                key "name";
                leaf name {
                  type string;
                }
              }
              list port-channel {
                tailf:cli-allow-join-with-key;
                tailf:cli-suppress-mode;
                tailf:cli-delete-when-empty;
                key "name";
                leaf name {
                  type string;
                }
              }
            }
          }
          list static-group {
            tailf:cli-suppress-mode;
            tailf:cli-delete-when-empty;
            key "group";
            leaf group {
              type inet:ipv4-address;
            }
            container interface {
              list Ethernet {
                tailf:cli-allow-join-with-key;
                tailf:cli-suppress-mode;
                tailf:cli-delete-when-empty;
                key "name";
                leaf name {
                  type string;
                }
              }
              list port-channel {
                tailf:cli-allow-join-with-key;
                tailf:cli-suppress-mode;
                tailf:cli-delete-when-empty;
                key "name";
                leaf name {
                  type string;
                }
              }
            }
          }
          choice spelling-choice {
            leaf optimise-multicast-flood {
              type boolean;
            }
            leaf optimised-multicast-flood {
              type boolean;
            }
          }
          container proxy {
            container general-queries {
              leaf mrt {
                type uint8;
              }
            }
          }
          container proxy-leave {
            leaf use-group-address {
              type empty;
            }
          }
          leaf querier {
            type inet:ipv4-address;
          }
          leaf querier-timeout {
            type uint16;
          }
          leaf query-interval {
            type uint16;
          }
          leaf query-max-response-time {
            type uint8;
          }
          container report-flood {
            leaf all {
              type empty;
            }
            list interface {
              tailf:cli-suppress-mode;
              tailf:cli-delete-when-empty;
              tailf:cli-compact-syntax;
              tailf:cli-sequence-commands;
              key "name";
              leaf name {
                type string;
              }
            }
          }
          list report-policy {
            tailf:cli-suppress-mode;
            tailf:cli-delete-when-empty;
            tailf:cli-compact-syntax;
            tailf:cli-sequence-commands;
            key "interface";
            leaf interface {
              tailf:cli-expose-key-name;
              type string;
            }
            choice prefix-key-choice {
              leaf prefix-list {
                tailf:cli-prefix-key;
                type string;
              }
              leaf route-map {
                tailf:cli-prefix-key;
                type string;
              }
            }
          }
          leaf report-suppression {
            type boolean;
          }
          leaf robustness-variable {
            type uint8;
          }
          leaf startup-query-count {
            type uint8;
          }
          leaf startup-query-interval {
            type uint16;
          }
          leaf group-timeout {
            type union {
              type uint16;
              type enumeration {
                enum "never";
              }
            }
          }
          leaf v3-report-suppression {
            type empty;
          }
          leaf version {
            type uint8;
          }
        }
      }
    }
    container service-policy {
      container type {
        container qos {
          container input {
            tailf:cli-compact-syntax;
            tailf:cli-sequence-commands;
            leaf name {
              tailf:cli-drop-node-name;
              type policy-map-name-type;
            }
            leaf no-stats {
              type empty;
            }
          }
          container output {
            tailf:cli-compact-syntax;
            tailf:cli-sequence-commands;
            leaf name {
              tailf:cli-drop-node-name;
              type policy-map-name-type;
            }
            leaf no-stats {
              type empty;
            }
          }
        }
      }
    }
  }

  grouping isis-spf-interval-grouping {
    leaf max-wait {
      tailf:cli-drop-node-name;
      type uint32;
    }
    leaf init-wait {
      tailf:cli-drop-node-name;
      type uint32;
    }
    leaf second-wait {
      tailf:cli-drop-node-name;
      type uint32;
    }
  }

  grouping isis-lsp-gen-interval-grouping {
    leaf max-wait {
      tailf:cli-drop-node-name;
      type uint32;
    }
    leaf init-wait {
      tailf:cli-drop-node-name;
      type uint32;
    }
    leaf second-wait {
      tailf:cli-drop-node-name;
      type uint32;
    }
  }

  grouping eigrp-interface-config-list-grouping {
    list eigrp {
      tailf:cli-suppress-mode;
      tailf:cli-delete-when-empty;
      key "id";
      leaf id {
        type string;
      }
    }
  }

  grouping eigrp-route-or-prefix-list-grouping {
    list eigrp {
      tailf:cli-suppress-mode;
      tailf:cli-delete-when-empty;
      key "id direction";
      leaf id {
        type string;
      }
      choice route-or-prefix-choice {
        leaf prefix-list {
          tailf:cli-prefix-key {
            tailf:cli-before-key "2";
          }
          type string;
        }
        leaf route-map {
          tailf:cli-prefix-key {
            tailf:cli-before-key "2";
          }
          type string;
        }
      }
      leaf direction {
        type enumeration {
          enum "in";
          enum "out";
        }
      }
    }
  }

  grouping lifetime-grouping {
    leaf local {
      tailf:cli-optional-in-sequence;
      type empty;
    }
    leaf start-time {
      tailf:cli-drop-node-name;
      type string;
    }
    leaf start-month {
      tailf:cli-drop-node-name;
      type short-month-type;
    }
    leaf start-day {
      tailf:cli-drop-node-name;
      type uint8;
    }
    leaf start-year {
      tailf:cli-drop-node-name;
      type uint16;
    }
    choice lifetime-choice {
      case end-explicit-time {
        leaf end-time {
          tailf:cli-drop-node-name;
          type string;
        }
        leaf end-month {
          tailf:cli-drop-node-name;
          type short-month-type;
        }
        leaf end-day {
          tailf:cli-drop-node-name;
          type uint8;
        }
        leaf end-year {
          tailf:cli-drop-node-name;
          type uint16;
        }
      }
      leaf duration {
        type uint32;
      }
      leaf infinite {
        type empty;
      }
    }
  }

  grouping queue-limit-grouping {
    choice limit-choice {
      case count {
        leaf count {
          tailf:cli-drop-node-name;
          must "../unit";
          type uint32;
        }
        leaf unit {
          tailf:cli-drop-node-name;
          type enumeration {
            enum "bytes";
            enum "kbytes";
            enum "mbytes";
            enum "ms";
            enum "packets";
            enum "us";
          }
        }
      }
      case percent {
        leaf percent {
          type uint8;
        }
      }
    }
  }

  grouping random-detect-grouping {
    container minimum-threshold {
      tailf:cli-sequence-commands {
        tailf:cli-reset-siblings;
      }
      tailf:cli-compact-syntax;
      tailf:cli-flatten-container;
      choice threshold-choice {
        case count {
          leaf count {
            tailf:cli-drop-node-name;
            must "../unit";
            type uint32;
          }
          leaf unit {
            tailf:cli-drop-node-name;
            type enumeration {
              enum "bytes";
              enum "kbytes";
              enum "mbytes";
            }
          }
        }
        leaf percent {
          type uint8;
        }
      }
    }
    container maximum-threshold {
      tailf:cli-sequence-commands {
        tailf:cli-reset-siblings;
      }
      tailf:cli-compact-syntax;
      tailf:cli-flatten-container;
      choice threshold-choice {
        case count {
          leaf count {
            tailf:cli-drop-node-name;
            must "../unit";
            type uint32;
          }
          leaf unit {
            tailf:cli-drop-node-name;
            type enumeration {
              enum "bytes";
              enum "kbytes";
              enum "mbytes";
            }
          }
        }
        leaf percent {
          type uint8;
        }
      }
    }
  }

  grouping itu-t-grouping {
    leaf ql {
      tailf:cli-drop-node-name;
      type enumeration {
        enum "exact";
        enum "highest";
        enum "lowest";
      }
    }
    container itu-t {
      tailf:cli-flatten-container;
      leaf option {
        type enumeration {
          enum "1";
          enum "2";
        }
      }
    }
    leaf option1-value {
      tailf:cli-drop-node-name;
      type enumeration {
        enum "DNU";
        enum "EEC1";
        enum "PRC";
        enum "PRTC";
        enum "SEC";
        enum "SSU-A";
        enum "SSU-B";
        enum "eEEC";
        enum "ePRTC";
      }
    }
    leaf generation {
      type enumeration {
        enum "1";
        enum "2";
      }
    }
    leaf option2-value {
      tailf:cli-drop-node-name;
      type itu-t-option2-type;
    }
    leaf highest {
      type itu-t-option2-type;
    }
  }

  grouping tcam-region-grouping {
    container region {
      container arp-ether-with-double-wide {
        tailf:cli-drop-node-name;
        tailf:cli-compact-syntax;
        tailf:cli-sequence-commands {
          tailf:cli-reset-siblings;
        }
        leaf arp-ether {
          type tcam-size-type;
        }
        leaf double-wide {
          type empty;
        }
      }
      leaf arp-ether {
        type tcam-size-type;
      }
      leaf copp {
        type tcam-size-type;
      }
      leaf e-qos {
        type tcam-size-type;
      }
      leaf e-racl {
        type tcam-size-type;
      }
      leaf ipv6-racl {
        type tcam-size-type;
      }
      leaf l3qos {
        type tcam-size-type;
      }
      leaf qos {
        type tcam-size-type;
      }
      leaf racl {
        type tcam-size-type;
      }
      leaf span {
        type tcam-size-type;
      }
      leaf vpc-convergence {
        type tcam-size-type;
      }
      leaf ipv6-l3qos {
        type tcam-size-type;
      }
      leaf e-ipv6-qos {
        type tcam-size-type;
      }
      leaf e-ipv6-racl {
        type tcam-size-type;
      }
      leaf e-mac-qos {
        type tcam-size-type;
      }
      leaf e-qos-lite {
        type tcam-size-type;
      }
      leaf fcoe-egress {
        type tcam-size-type;
      }
      leaf fcoe-ingress {
        type tcam-size-type;
      }
      leaf fex-ifacl {
        type tcam-size-type;
      }
      leaf fex-ipv6-ifacl {
        type tcam-size-type;
      }
      leaf fex-ipv6-qos {
        type tcam-size-type;
      }
      leaf fex-mac-ifacl {
        type tcam-size-type;
      }
      leaf fex-mac-qos {
        type tcam-size-type;
      }
      leaf fex-qos {
        type tcam-size-type;
      }
      leaf fex-qos-lite {
        type tcam-size-type;
      }
      leaf flow {
        type tcam-size-type;
      }
      leaf ifacl {
        type tcam-size-type;
      }
      leaf ipsg {
        type tcam-size-type;
      }
      leaf ipv6-ifacl {
        type tcam-size-type;
      }
      leaf ipv6-qos {
        type tcam-size-type;
      }
      leaf ipv6-vacl {
        type tcam-size-type;
      }
      leaf ipv6-vqos {
        type tcam-size-type;
      }
      leaf l3qos-lite {
        type tcam-size-type;
      }
      leaf mac-ifacl {
        type tcam-size-type;
      }
      leaf mac-l3qos {
        type tcam-size-type;
      }
      leaf mac-qos {
        type tcam-size-type;
      }
      leaf mac-vacl {
        type tcam-size-type;
      }
      leaf mac-vqos {
        type tcam-size-type;
      }
      leaf mcast-performance {
        type tcam-size-type;
      }
      leaf mcast_bidir {
        type tcam-size-type;
      }
      leaf mpls {
        type tcam-size-type;
      }
      leaf nat {
        type tcam-size-type;
      }
      leaf ns-ipv6-l3qos {
        type tcam-size-type;
      }
      leaf ns-ipv6-qos {
        type tcam-size-type;
      }
      leaf ns-ipv6-vqos {
        type tcam-size-type;
      }
      leaf ns-l3qos {
        type tcam-size-type;
      }
      leaf ns-mac-l3qos {
        type tcam-size-type;
      }
      leaf ns-mac-qos {
        type tcam-size-type;
      }
      leaf ns-mac-vqos {
        type tcam-size-type;
      }
      leaf ns-qos {
        type tcam-size-type;
      }
      leaf ns-vqos {
        type tcam-size-type;
      }
      leaf openflow {
        type tcam-size-type;
      }
      leaf openflow-ipv6 {
        type tcam-size-type;
      }
      leaf qos-lite {
        type tcam-size-type;
      }
      leaf redirect {
        type tcam-size-type;
      }
      leaf redirect_v4 {
        type tcam-size-type;
      }
      leaf redirect_v6 {
        type tcam-size-type;
      }
      leaf redirect-tunnel {
        type tcam-size-type;
      }
      leaf rp-ipv6-qos {
        type tcam-size-type;
      }
      leaf rp-mac-qos {
        type tcam-size-type;
      }
      leaf rp-qos {
        type tcam-size-type;
      }
      leaf rp-qos-lite {
        type tcam-size-type;
      }
      leaf sflow {
        type tcam-size-type;
      }
      leaf span-sflow {
        type tcam-size-type;
      }
      leaf svi {
        type tcam-size-type;
      }
      leaf vacl {
        type tcam-size-type;
      }
      leaf e-vacl {
        type tcam-size-type;
      }
      leaf vqos {
        type tcam-size-type;
      }
      leaf vqos-lite {
        type tcam-size-type;
      }
      leaf ing-fstat {
        type tcam-size-type;
      }
      leaf ing-ifacl {
        type tcam-size-type;
      }
      leaf ing-l2-qos {
        type tcam-size-type;
      }
      leaf ing-l2-span-filter {
        type tcam-size-type;
      }
      leaf ing-l3-span-filter {
        type tcam-size-type;
      }
      leaf ing-l3-vlan-qos {
        type tcam-size-type;
      }
      leaf ing-nbm {
        type tcam-size-type;
      }
      leaf ing-racl {
        type tcam-size-type;
      }
      leaf ing-rbacl {
        type tcam-size-type;
      }
      leaf ing-flow-redirect {
        type tcam-size-type;
      }
      leaf ing-redirect {
        type tcam-size-type;
      }
      leaf ing-sup {
        type tcam-size-type;
      }
      leaf ing-mvpn {
        type tcam-size-type;
      }
      leaf egr-l2-qos {
        type tcam-size-type;
      }
      leaf egr-l3-vlan-qos {
        type tcam-size-type;
      }
      leaf egr-racl {
        type tcam-size-type;
      }
      leaf egr-sup {
        type tcam-size-type;
      }
      leaf ing-netflow {
        type tcam-size-type;
      }
    }
  }

  container EXEC {
    tailf:cli-drop-node-name;
  }
  leaf version {
    tailf:cli-multi-value;
    type string;
  }
  container license {
    leaf grace-period {
      type boolean;
    }
    container smart {
      leaf transport {
        type enumeration {
          enum "off";
          enum "callhome";
          enum "cslu";
          enum "smart";
        }
      }
      container url {
        leaf cslu {
          type string;
        }
        leaf smart {
          type string;
        }
      }
    }
  }
  leaf hostname {
    type string;
  }
  leaf switchname {
    type string;
  }
  container feature {
    leaf analytics {
      type empty;
    }
    leaf bash-shell {
      type empty;
    }
    leaf bgp {
      type empty;
    }
    leaf bfd {
      type empty;
    }
    leaf cable-management {
      type empty;
    }
    leaf dot1x {
      type empty;
    }
    leaf cts {
      type empty;
    }
    leaf eigrp {
      type empty;
    }
    leaf ethernet-link-oam {
      type empty;
    }
    leaf evmed {
      type empty;
    }
    container fabric {
      leaf access {
        type empty;
      }
      leaf forwarding {
        type empty;
      }
      leaf multicast {
        type empty;
      }
    }
    leaf fabricpath-vpn {
      type empty;
    }
    leaf fabric-binding {
      type empty;
    }
    leaf fcoe {
      type empty;
    }
    leaf fcoe-npv {
      type empty;
    }
    leaf frequency-synchronization {
      type empty;
    }
    leaf fex {
      type empty;
    }
    leaf fport-channel-trunk {
      type empty;
    }
    leaf grpc {
      type empty;
    }
    leaf glbp {
      type empty;
    }
    leaf flexlink {
      type empty;
    }
    leaf hardware-telemetry {
      type empty;
    }
    leaf hsrp {
      type empty;
    }
    leaf intersight {
      type empty;
    }
    leaf icam {
      type empty;
    }
    leaf itd {
      type empty;
    }
    leaf macsec {
      type empty;
    }
    leaf msdp {
      type empty;
    }
    container mpls {
      leaf l2vpn {
        type empty;
      }
      leaf l3vpn {
        type empty;
      }
      leaf ldp {
        type empty;
      }
      container srte {
        tailf:cli-drop-node-name;
        container segment-routing {
          leaf traffic-engineering {
            type empty;
          }
        }
      }
      leaf segment-routing {
        type empty;
      }
      leaf evpn {
        type empty;
      }
      leaf oam {
        type empty;
      }
    }
    leaf nat {
      type empty;
    }
    leaf ngmvpn {
      type empty;
    }
    leaf ngoam {
      type empty;
    }
    leaf npiv {
      type empty;
    }
    leaf npv {
      type empty;
    }
    leaf ntp {
      type empty;
    }
    container nv {
      leaf overlay {
        type empty;
      }
    }
    leaf nxapi {
      type empty;
    }
    leaf nxdb {
      type empty;
    }
    leaf network-segmentation-manager {
      type empty;
    }
    leaf lisp {
      type empty;
    }
    leaf ldap {
      type empty;
    }
    leaf lldp {
      type empty;
    }
    leaf pbr {
      type empty;
    }
    leaf ospf {
      type empty;
    }
    leaf ospfv3 {
      type empty;
    }
    leaf otv {
      type empty;
    }
    container password {
      container encryption {
        leaf aes {
          type empty;
        }
      }
    }
    leaf pim {
      type empty;
    }
    leaf pim6 {
      type empty;
    }
    leaf poe {
      type empty;
    }
    leaf pong {
      type empty;
    }
    leaf port-security {
      type empty;
    }
    leaf privilege {
      type empty;
    }
    leaf ptp {
      type empty;
    }
    leaf restconf {
      type empty;
    }
    leaf rip {
      type empty;
    }
    leaf segmentation {
      type empty;
    }
    leaf scheduler {
      type empty;
    }
    leaf scp-server {
      type empty;
    }
    leaf sftp-server {
      type empty;
    }
    leaf sflow {
      type empty;
    }
    leaf signature-verification {
      type empty;
    }
    container sla {
      leaf responder {
        type empty;
      }
      leaf sender {
        type empty;
      }
    }
    leaf udld {
      type empty;
    }
    leaf vni {
      type empty;
    }
    leaf vn-segment-vlan-based {
      type empty;
    }
    leaf vpc {
      type empty;
    }
    leaf vrrp {
      type empty;
    }
    leaf vrrpv3 {
      type empty;
    }
    leaf vtp {
      type empty;
    }
    leaf dhcp {
      type empty;
    }
    leaf http-server {
      type empty;
    }
    leaf imp {
      type empty;
    }
    leaf interface-vlan {
      type empty;
    }
    leaf isis {
      type empty;
    }
    leaf lacp {
      type empty;
    }
    leaf netconf {
      type empty;
    }
    leaf netflow {
      type empty;
    }
    leaf port-profile-roles {
      type empty;
    }
    leaf private-vlan {
      type empty;
    }
    leaf ssh {
      type empty;
    }
    leaf tacacs-plus {
      tailf:alt-name "tacacs+";
      type empty;
    }
    leaf telemetry {
      type empty;
    }
    leaf telnet {
      type empty;
    }
    leaf tunnel {
      type empty;
    }
    leaf vpd {
      type empty;
    }
    container license {
      leaf smart {
        type empty;
      }
    }
    leaf openconfig {
      type empty;
    }
  }
  container password {
    leaf strength-check {
      type boolean;
    }
    leaf secure-mode {
      type boolean;
    }
  }
  leaf fabric-mode {
    tailf:cli-case-insensitive;
    type enumeration {
      enum "10g";
      enum "40g";
    }
  }
  container poweroff {
    leaf module {
      type uint8;
    }
  }
  container power {
    tailf:cli-compact-syntax;
    tailf:cli-sequence-commands {
      tailf:cli-reset-siblings;
    }
    leaf redundancy-mode {
      type enumeration {
        enum "combined";
        enum "insrc-redundant";
        enum "ps-redundant";
        enum "redundant";
      }
    }
    leaf force {
      type empty;
    }
  }
  container nv {
    container overlay {
      leaf evpn {
        type empty;
      }
    }
  }
  container vni {
    leaf-list vni {
      tailf:cli-drop-node-name;
      tailf:cli-range-list-syntax;
      type uint32;
    }
  }
  container tacacs-server {
    tailf:cli-compact-syntax;
    leaf deadtime {
      type uint16;
    }
    leaf directed-request {
      type empty;
    }
    list host {
      tailf:cli-compact-syntax;
      tailf:cli-suppress-mode;
      tailf:cli-delete-when-empty;
      ordered-by user;
      key "id";
      leaf id {
        type union {
          type inet:ipv4-address;
          type inet:ipv6-address;
          type string;
        }
      }
      container secret {
        tailf:cli-drop-node-name;
        tailf:cli-flatten-container;
        tailf:cli-compact-syntax;
        tailf:cli-sequence-commands;
        leaf key {
          type enumeration {
            enum "0";
            enum "6";
            enum "7";
          }
        }
        leaf shared-secret {
          tailf:cli-drop-node-name;
          type string;
        }
      }
      leaf port {
        type uint16;
      }
      container test {
        tailf:cli-flatten-container;
        tailf:cli-optional-in-sequence;
        leaf idle-time {
          type uint16;
        }
        leaf password {
          type string;
        }
        leaf username {
          type string;
        }
      }
      leaf timeout {
        type uint8;
      }
    }
    container secret {
      tailf:cli-drop-node-name;
      tailf:cli-compact-syntax;
      tailf:cli-sequence-commands {
        tailf:cli-reset-siblings;
      }
      leaf key {
        type enumeration {
          enum "0";
          enum "6";
          enum "7";
        }
      }
      leaf shared-secret {
        tailf:cli-drop-node-name;
        type string;
      }
    }
    container test {
      leaf idle-time {
        type uint16;
      }
      leaf password {
        type string;
      }
      leaf username {
        type string;
      }
    }
    leaf timeout {
      type uint8;
    }
  }
  container radius-server {
    leaf deadtime {
      type uint16;
    }
    leaf directed-request {
      type empty;
    }
    list host {
      tailf:cli-compact-syntax;
      tailf:cli-suppress-mode;
      tailf:cli-delete-when-empty;
      ordered-by user;
      key "id";
      leaf id {
        type union {
          type inet:ip-address;
          type inet:ipv6-address;
          type string;
        }
      }
      container key {
        tailf:cli-flatten-container;
        tailf:cli-compact-syntax;
        tailf:cli-sequence-commands {
          tailf:cli-reset-siblings;
        }
        leaf encryption {
          tailf:cli-drop-node-name;
          type enumeration {
            enum "0";
            enum "7";
            enum "6";
          }
        }
        leaf password {
          tailf:cli-drop-node-name;
          type string;
        }
      }
      leaf pac {
        type empty;
      }
      leaf auth-port {
        type uint16;
      }
      leaf acct-port {
        type uint16;
      }
      leaf authentication {
        type empty;
      }
      leaf accounting {
        type empty;
      }
      leaf timeout {
        type uint8;
      }
      leaf retransmit {
        type uint8;
      }
    }
    container key {
      tailf:cli-compact-syntax;
      tailf:cli-sequence-commands;
      leaf encryption {
        tailf:cli-drop-node-name;
        type enumeration {
          enum "0";
          enum "7";
          enum "6";
        }
      }
      leaf password {
        tailf:cli-drop-node-name;
        type string;
      }
    }
    leaf retransmit {
      type uint8;
    }
    leaf timeout {
      type uint8;
    }
  }
  container ldap {
    list search-map {
      key "name";
      leaf name {
        type string;
      }
      container CRLLookup {
        tailf:cli-compact-syntax;
        tailf:cli-sequence-commands {
          tailf:cli-reset-siblings;
        }
        uses ldap-attr-filter-grouping;
      }
      container trustedCert {
        tailf:cli-compact-syntax;
        tailf:cli-sequence-commands {
          tailf:cli-reset-siblings;
        }
        uses ldap-attr-filter-grouping;
      }
      container user-certdn-match {
        tailf:cli-compact-syntax;
        tailf:cli-sequence-commands {
          tailf:cli-reset-siblings;
        }
        uses ldap-attr-filter-grouping;
      }
      container user-pubkey-match {
        tailf:cli-compact-syntax;
        tailf:cli-sequence-commands {
          tailf:cli-reset-siblings;
        }
        uses ldap-attr-filter-grouping;
      }
      container user-switch-bind {
        tailf:cli-compact-syntax;
        tailf:cli-sequence-commands {
          tailf:cli-reset-siblings;
        }
        uses ldap-attr-filter-grouping;
      }
      container userprofile {
        tailf:cli-compact-syntax;
        tailf:cli-sequence-commands {
          tailf:cli-reset-siblings;
        }
        uses ldap-attr-filter-grouping;
      }
    }
  }

  grouping ldap-attr-filter-grouping {
    leaf attribute-name {
      type string;
    }
    leaf search-filter {
      type string;
    }
    leaf base-DN {
      type string;
    }
  }

  container ldap-server {
    leaf deadtime {
      type uint8;
    }
    leaf timeout {
      type uint8;
    }
    list host {
      tailf:cli-suppress-mode;
      tailf:cli-delete-when-empty;
      key "name";
      ordered-by user;
      leaf name {
        type string;
      }
      leaf enable-ssl {
        type empty;
      }
      leaf referral-disable {
        type empty;
      }
      container host-config {
        tailf:cli-drop-node-name;
        tailf:cli-sequence-commands {
          tailf:cli-reset-siblings;
        }
        tailf:cli-compact-syntax;
        leaf rootDN {
          type string;
        }
        container password {
          tailf:cli-flatten-container;
          tailf:cli-compact-syntax;
          tailf:cli-sequence-commands {
            tailf:cli-reset-siblings;
          }
          leaf encrypted {
            tailf:alt-name "7";
            tailf:cli-optional-in-sequence;
            type empty;
          }
          leaf password {
            tailf:cli-drop-node-name;
            type string;
          }
        }
        leaf port {
          tailf:cli-optional-in-sequence;
          type uint16;
        }
        leaf timeout {
          type uint8;
        }
      }
    }
  }
  container aaa {
    container group {
      container server {
        list radius {
          key "id";
          leaf id {
            type string;
          }
          leaf deadtime {
            type uint16;
          }
          list server {
            tailf:cli-suppress-mode;
            ordered-by user;
            key "id";
            leaf id {
              type union {
                type inet:ip-address;
                type inet:ipv6-address;
                type string;
              }
            }
          }
          container source-interface {
            leaf Ethernet {
              tailf:cli-allow-join-with-value;
              type string;
            }
            leaf loopback {
              tailf:cli-allow-join-with-value;
              type uint16;
            }
            leaf mgmt {
              tailf:cli-allow-join-with-value;
              type uint16;
            }
            leaf Null {
              tailf:cli-allow-join-with-value;
              type uint16;
            }
            leaf port-channel {
              tailf:cli-allow-join-with-value;
              type uint16;
            }
            leaf sup-eth {
              tailf:cli-allow-join-with-value;
              type uint16;
            }
            leaf vlan {
              tailf:cli-allow-join-with-value;
              type uint16;
            }
          }
          leaf use-vrf {
            type vrf-member-type;
          }
        }
        list tacacs-plus {
          tailf:alt-name "tacacs+";
          key "id";
          leaf id {
            type string;
          }
          list server {
            tailf:cli-suppress-mode;
            ordered-by user;
            key "id";
            leaf id {
              type string;
            }
          }
          leaf source-interface {
            type string;
          }
          leaf use-vrf {
            type vrf-member-type;
          }
          leaf deadtime {
            type uint16;
          }
        }
        list ldap {
          key "name";
          leaf name {
            type string;
          }
          container authentication {
            container bind-first {
              presence "true";
              leaf append-with-basedn {
                type string;
              }
            }
            container compare {
              presence "true";
              leaf password-attribute {
                type string;
              }
            }
          }
          container enable {
            leaf Cert-DN-match {
              type empty;
            }
            leaf user-server-group {
              type empty;
            }
          }
          leaf ldap-search-map {
            type string;
          }
          list server {
            tailf:cli-suppress-mode;
            ordered-by user;
            key "name";
            leaf name {
              type string;
            }
          }
          leaf deadtime {
            type uint16;
          }
        }
      }
    }
    container server {
      container radius {
        container dynamic-author {
          tailf:cli-add-mode;
          presence "true";
          list client {
            tailf:cli-suppress-mode;
            tailf:cli-delete-when-empty;
            tailf:cli-compact-syntax;
            key "addr";
            leaf addr {
              type union {
                type inet:ipv4-address;
                type inet:ipv6-address;
                type string;
              }
            }
            leaf vrf {
              type vrf-member-type;
            }
            container server-key {
              leaf cisco_enc {
                tailf:alt-name "7";
                type string;
              }
            }
          }
        }
      }
    }
    container accounting {
      container default {
        leaf-list group {
          tailf:cli-flat-list-syntax;
          ordered-by user;
          type string;
        }
        leaf local {
          type boolean;
        }
      }
      container dot1x {
        container default {
          leaf-list group {
            tailf:cli-flat-list-syntax;
            type string;
          }
        }
      }
    }
    container authentication {
      container login {
        leaf ascii-authentication {
          type empty;
        }
        leaf chap {
          type enable-type;
        }
        container fallback-local {
          tailf:cli-drop-node-name;

          grouping fallback-grouping {
            container fallback {
              container error {
                leaf local {
                  type boolean;
                }
              }
            }
          }
          container console {
            uses fallback-grouping;
          }
          container default {
            uses fallback-grouping;
          }
        }
        container console {
          tailf:cli-sequence-commands {
            tailf:cli-reset-siblings;
          }
          tailf:cli-compact-syntax;
          uses groups-and-fallback-grouping;
        }
        container default {
          tailf:cli-sequence-commands {
            tailf:cli-reset-siblings;
          }
          tailf:cli-compact-syntax;
          uses groups-and-fallback-grouping;
        }
        leaf error-enable {
          type empty;
        }
        leaf invalid-username-log {
          type empty;
        }
        leaf mschap {
          type enable-type;
        }
        leaf mschapv2 {
          type enable-type;
        }
      }
      container dot1x {
        container default {
          leaf-list group {
            tailf:cli-flat-list-syntax;
            type string;
          }
        }
      }
      container cts {
        container default {
          leaf-list group {
            tailf:cli-flat-list-syntax;
            type string;
          }
        }
      }
    }
    container authorization {
      container commands {
        tailf:cli-compact-syntax;
        container console {
          tailf:cli-sequence-commands;
          tailf:cli-compact-syntax;
          uses groups-and-fallback-grouping;
        }
        container default {
          tailf:cli-sequence-commands;
          tailf:cli-compact-syntax;
          uses groups-and-fallback-grouping;
        }
      }
      container config-commands {
        tailf:cli-compact-syntax;
        container console {
          tailf:cli-sequence-commands;
          tailf:cli-compact-syntax;
          uses groups-and-fallback-grouping;
        }
        container default {
          tailf:cli-sequence-commands;
          tailf:cli-compact-syntax;
          uses groups-and-fallback-grouping;
        }
      }
      container ssh-certificate {
        container default {
          leaf group {
            type string;
          }
          leaf local {
            type boolean;
          }
        }
      }
      container ssh-publickey {
        container default {
          leaf group {
            type string;
          }
          leaf local {
            type boolean;
          }
        }
      }
      container cts {
        container default {
          leaf-list group {
            tailf:cli-flat-list-syntax;
            type string;
          }
        }
      }
    }
    container user {
      leaf default-role {
        type empty;
      }
    }
    list bypass-user {
      tailf:cli-suppress-mode;
      tailf:cli-delete-when-empty;
      tailf:cli-compact-syntax;
      key "name";
      leaf name {
        type string;
      }
      leaf accounting {
        type empty;
      }
      leaf authorization {
        type empty;
      }
    }
  }

  grouping groups-and-fallback-grouping {
    leaf group {
      tailf:cli-optional-in-sequence;
      type string;
    }
    leaf group2 {
      tailf:cli-optional-in-sequence;
      tailf:cli-drop-node-name;
      type string;
    }
    leaf group3 {
      tailf:cli-optional-in-sequence;
      tailf:cli-drop-node-name;
      type string;
    }
    leaf fallback {
      tailf:cli-drop-node-name;
      type enumeration {
        enum "local";
        enum "none";
      }
    }
  }

  container acllog {
    leaf match-log-level {
      type uint8;
    }
  }
  container segment {
    container mode {
      leaf unicast-only {
        type boolean;
      }
    }
    container control-protocol {
      leaf bgp {
        type boolean;
      }
    }
  }
  container enable {
    container secret {
      tailf:cli-compact-syntax;
      tailf:cli-sequence-commands {
        tailf:cli-reset-siblings;
      }
      leaf type {
        tailf:cli-drop-node-name;
        tailf:cli-optional-in-sequence;
        type enumeration {
          enum "0";
          enum "5";
        }
      }
      leaf secret {
        tailf:cli-drop-node-name;
        type string;
      }
    }
  }
  container cfs {
    leaf distribute {
      type empty;
    }
    container eth {
      leaf distribute {
        type empty;
      }
    }
    container ipv4 {
      leaf distribute {
        type empty;
      }
      leaf mcast-address {
        type inet:ipv4-address;
      }
    }
    leaf region {
      type uint8;
    }
    leaf static-peers {
      type empty;
    }
  }
  container cts {
    container cache {
      leaf enable {
        type empty;
      }
    }
    container device-id {
      tailf:cli-compact-syntax;
      tailf:cli-sequence-commands {
        tailf:cli-reset-siblings;
      }
      leaf name {
        tailf:cli-drop-node-name;
        type string;
      }
      container password {
        tailf:cli-flatten-container;
        choice pwd-type-choice {
          leaf cisco_enc {
            tailf:alt-name "7";
            type string;
          }
          leaf clear {
            tailf:cli-drop-node-name;
            type string;
          }
        }
      }
    }
    container role-based {
      container counters {
        leaf enable {
          type empty;
        }
      }
      list sgt-map {
        tailf:cli-suppress-mode;
        tailf:cli-delete-when-empty;
        key "addr";
        leaf addr {
          type union {
            type inet:ipv4-address;
            type tailf:ipv4-address-and-prefix-length;
          }
        }
        leaf sgt {
          tailf:cli-drop-node-name;
          type uint16;
        }
      }
      leaf enforcement {
        type empty;
      }
    }
    leaf sgt {
      type string;
    }
    container sxp {
      leaf enable {
        type empty;
      }
      container default {
        container password {
          choice pwd-type-choice {
            leaf cisco_enc {
              tailf:alt-name "7";
              type string;
            }
            leaf clear {
              tailf:cli-drop-node-name;
              type string;
            }
          }
        }
        leaf source-ip {
          type inet:ipv4-address;
        }
      }
      container connection {
        list peer {
          tailf:cli-suppress-mode;
          tailf:cli-delete-when-empty;
          tailf:cli-compact-syntax;
          tailf:cli-sequence-commands {
            tailf:cli-reset-siblings;
          }
          key "addr vrf";
          leaf addr {
            type inet:ipv4-address;
          }
          leaf source {
            tailf:cli-optional-in-sequence;
            tailf:cli-prefix-key {
              tailf:cli-before-key "2";
            }
            type inet:ipv4-address;
          }
          leaf password {
            tailf:cli-prefix-key {
              tailf:cli-before-key "2";
            }
            type enumeration {
              enum "default";
              enum "none";
              enum "required";
            }
          }
          leaf cisco_enc {
            tailf:cli-optional-in-sequence;
            tailf:cli-prefix-key {
              tailf:cli-before-key "2";
            }
            tailf:alt-name "7";
            type string;
          }
          leaf mode {
            tailf:cli-prefix-key {
              tailf:cli-before-key "2";
            }
            type enumeration {
              enum "listener";
              enum "speaker";
            }
          }
          leaf vrf {
            tailf:cli-expose-key-name;
            type vrf-member-type;
          }
        }
      }
    }
  }
  list username {
    tailf:cli-suppress-mode;
    tailf:cli-delete-when-empty;
    tailf:cli-compact-syntax;
    tailf:cli-sequence-commands {
      tailf:cli-reset-siblings;
    }
    key "name";
    leaf name {
      type string;
    }
    container password {
      tailf:cli-compact-syntax;
      tailf:cli-flatten-container;
      tailf:cli-sequence-commands;
      leaf encryption {
        tailf:cli-drop-node-name;
        type enumeration {
          enum "0";
          enum "5";
          enum "8";
          enum "9";
        }
      }
      leaf password {
        tailf:cli-drop-node-name;
        type string;
      }
    }
    leaf crypt-type {
      tailf:cli-drop-node-name;
      tailf:cli-optional-in-sequence;
      type enumeration {
        enum "pbkdf2";
        enum "scrypt";
      }
    }
    leaf expire {
      tailf:cli-optional-in-sequence;
      type string;
    }
    leaf role {
      type user-role-type;
    }
  }
  container username-secondary-roles {
    tailf:cli-drop-node-name;
    list username {
      tailf:cli-suppress-mode;
      tailf:cli-delete-when-empty;
      key "name role";
      leaf name {
        type string;
      }
      leaf role {
        tailf:cli-expose-key-name;
        type user-role-type;
      }
    }
  }
  container username-config {
    tailf:cli-drop-node-name;
    list username {
      tailf:cli-suppress-mode;
      tailf:cli-delete-when-empty;
      key "name";
      leaf name {
        type string;
      }
      container sshkey {
        leaf file {
          type string;
        }
        leaf openssh-key {
          tailf:cli-drop-node-name;
          tailf:cli-multi-value;
          type string;
        }
      }
      container passphrase {
        tailf:cli-compact-syntax;
        leaf gracetime {
          type uint32;
        }
        leaf lifetime {
          type uint32;
        }
        leaf warntime {
          type uint32;
        }
      }
      container keypair {
        container generate {
          leaf rsa {
            type empty;
          }
        }
      }
      leaf shelltype {
        type enumeration {
          enum "bash";
          enum "vsh";
        }
      }
    }
  }
  container nxapi {
    container http {
      leaf port {
        type uint16;
      }
    }
    container https {
      leaf port {
        type uint16;
      }
    }
    leaf use-vrf {
      type vrf-member-type;
    }
  }
  container banner {

    grouping banner-body-grouping {
      leaf start-marker {
        tailf:cli-drop-node-name;
        type string;
      }
      leaf message {
        tailf:cli-drop-node-name;
        type string;
      }
      leaf end-marker {
        tailf:cli-drop-node-name;
        type string;
        must "../end-marker = ../start-marker";
      }
    }
    container exec {
      tailf:cli-sequence-commands {
        tailf:cli-reset-siblings;
      }
      tailf:cli-compact-syntax;
      uses banner-body-grouping;
    }
    container motd {
      tailf:cli-sequence-commands {
        tailf:cli-reset-siblings;
      }
      tailf:cli-compact-syntax;
      uses banner-body-grouping;
    }
  }
  container ssh {
    container key {
      leaf rsa {
        type uint16;
      }
    }
    leaf login-attempts {
      type uint8;
    }
    leaf ciphers {
      type enumeration {
        enum "aes256-gcm";
        enum "all";
      }
    }
    container ciphers-algs {
      tailf:cli-drop-node-name;
      container ciphers {
        list no-list {
          tailf:cli-suppress-mode;
          tailf:cli-delete-when-empty;
          key "name";
          leaf name {
            type string;
          }
        }
      }
    }
    leaf kexalgos {
      type enumeration {
        enum "all";
        enum "ecdh-sha2-nistp384";
      }
    }
    container kexalgos-algs {
      tailf:cli-drop-node-name;
      container kexalgos {
        list no-list {
          tailf:cli-suppress-mode;
          tailf:cli-delete-when-empty;
          key "name";
          leaf name {
            type string;
          }
        }
      }
    }
    leaf keytypes {
      type enumeration {
        enum "all";
      }
    }
    container keytypes-algs {
      tailf:cli-drop-node-name;
      container keytypes {
        list no-list {
          tailf:cli-suppress-mode;
          tailf:cli-delete-when-empty;
          key "name";
          leaf name {
            type string;
          }
        }
      }
    }
    leaf macs {
      type enumeration {
        enum "all";
      }
    }
    container macs-algs {
      tailf:cli-drop-node-name;
      container macs {
        list no-list {
          tailf:cli-suppress-mode;
          tailf:cli-delete-when-empty;
          key "name";
          leaf name {
            type string;
          }
        }
      }
    }
  }
  container fabric {
    container forwarding {
      leaf anycast-gateway-mac {
        type string;
      }
    }
  }
  container fabricpath {
    container domain {
      container default {
        tailf:cli-add-mode;
        presence "true";
        container spf-interval {
          tailf:cli-compact-syntax;
          tailf:cli-sequence-commands;
          uses isis-spf-interval-grouping;
        }
        container lsp-gen-interval {
          tailf:cli-compact-syntax;
          tailf:cli-sequence-commands;
          uses isis-lsp-gen-interval-grouping;
        }
        leaf root-priority {
          type uint8;
        }
        container set-overload-bit {
          tailf:cli-sequence-commands {
            tailf:cli-reset-siblings;
          }
          tailf:cli-compact-syntax;
          choice always-or-startup-choice {
            leaf always {
              type empty;
            }
            leaf on-startup {
              type uint32;
            }
          }
        }
        container fabricpath {
          container isis {
            list event-history {
              tailf:cli-suppress-mode;
              tailf:cli-delete-when-empty;
              key "event";
              leaf event {
                type enumeration {
                  enum "adjacency";
                  enum "cli";
                  enum "csnp";
                  enum "drap";
                  enum "events";
                  enum "graceful";
                  enum "ha";
                  enum "iih";
                  enum "lsp-flood";
                  enum "lsp-gen";
                  enum "m2rib";
                  enum "mccast";
                  enum "psnp";
                  enum "redist";
                  enum "spf-leaf";
                  enum "spf-tree";
                  enum "urib";
                }
              }
              leaf size {
                type union {
                  type enumeration {
                    enum "disabled";
                    enum "large";
                    enum "medium";
                    enum "small";
                  }
                  type uint32;
                }
              }
            }
          }
        }
        container address-family {
          container ipv4 {
            container unicast {
              presence "true";
            }
          }
          container ipv6 {
            container unicast {
              presence "true";
            }
          }
        }
        list topology {
          key "id";
          leaf id {
            type uint8;
          }
          leaf maximum-paths {
            type uint8;
          }
          container reference-bandwidth {
            tailf:cli-sequence-commands {
              tailf:cli-reset-siblings;
            }
            tailf:cli-compact-syntax;
            leaf value {
              tailf:cli-drop-node-name;
              type uint32;
            }
            leaf Mbps {
              type empty;
            }
          }
          leaf root-priority {
            type uint8;
          }
        }
      }
    }
    container graceful-merge {
      leaf disable {
        type empty;
      }
    }
    container mode {
      leaf transit {
        type empty;
      }
    }
    leaf switch-id {
      type uint16;
    }
    container timers {
      leaf linkup-delay {
        type union {
          type uint16;
          type enumeration {
            enum "always";
          }
        }
      }
    }
    container ttl {
      leaf multicast {
        type uint8;
      }
      leaf unicast {
        type uint8;
      }
    }
  }
  container ip {
    container as-path {
      list access-list {
        tailf:cli-suppress-mode;
        tailf:cli-delete-when-empty;
        key "name";
        leaf name {
          type string;
        }
        list seq {
          tailf:cli-suppress-mode;
          tailf:cli-delete-when-empty;
          tailf:cli-compact-syntax;
          tailf:cli-sequence-commands {
            tailf:cli-reset-siblings;
          }
          key "num";
          leaf num {
            type uint32;
          }
          leaf action {
            tailf:cli-drop-node-name;
            type enumeration {
              enum "deny";
              enum "permit";
            }
          }
          leaf regex {
            tailf:cli-drop-node-name;
            type string;
          }
        }
        list unsequenced {
          tailf:cli-drop-node-name;
          tailf:cli-suppress-mode;
          tailf:cli-delete-when-empty;
          ordered-by user;
          key "regex";
          leaf regex {
            type string;
          }
          leaf action {
            tailf:cli-prefix-key;
            tailf:cli-drop-node-name;
            type enumeration {
              enum "deny";
              enum "permit";
            }
          }
        }
      }
    }
    container community-list {
      list standard {
        tailf:cli-suppress-mode;
        tailf:cli-delete-when-empty;
        key "name";
        leaf name {
          type string;
        }
        choice entry-syntax-choice {
          list entry {
            tailf:cli-drop-node-name;
            tailf:cli-suppress-mode;
            tailf:cli-delete-when-empty;
            ordered-by user;
            key "community-spec";
            leaf community-spec {
              tailf:cli-multi-word-key;
              type string;
            }
            leaf type {
              tailf:cli-drop-node-name;
              tailf:cli-prefix-key;
              mandatory true;
              type enumeration {
                enum "deny";
                enum "permit";
              }
            }
          }
          list seq-entry {
            tailf:cli-drop-node-name;
            tailf:cli-suppress-mode;
            tailf:cli-delete-when-empty;
            tailf:cli-sequence-commands {
              tailf:cli-reset-siblings;
            }
            tailf:cli-compact-syntax;
            key "seq";
            leaf seq {
              tailf:cli-expose-key-name;
              type uint32;
            }
            leaf type {
              tailf:cli-drop-node-name;
              mandatory true;
              type enumeration {
                enum "deny";
                enum "permit";
              }
            }
            leaf-list community {
              tailf:cli-drop-node-name;
              tailf:cli-flat-list-syntax;
              type union {
                type enumeration {
                  enum "internet";
                  enum "local-AS";
                  enum "no-advertise";
                  enum "no-export";
                }
                type string;
              }
            }
          }
        }
      }
      list expanded {
        tailf:cli-suppress-mode;
        tailf:cli-delete-when-empty;
        key "name";
        leaf name {
          type string;
        }
        choice entry-syntax-choice {
          list entry {
            tailf:cli-drop-node-name;
            tailf:cli-suppress-mode;
            tailf:cli-delete-when-empty;
            ordered-by user;
            key "regexp";
            leaf regexp {
              tailf:cli-multi-word-key;
              type string;
            }
            leaf type {
              tailf:cli-drop-node-name;
              tailf:cli-prefix-key;
              mandatory true;
              type enumeration {
                enum "deny";
                enum "permit";
              }
            }
          }
          list seq-entry {
            tailf:cli-drop-node-name;
            tailf:cli-suppress-mode;
            tailf:cli-delete-when-empty;
            tailf:cli-compact-syntax;
            tailf:cli-sequence-commands {
              tailf:cli-reset-siblings;
            }
            key "seq";
            leaf seq {
              tailf:cli-expose-key-name;
              type uint32;
            }
            leaf type {
              tailf:cli-drop-node-name;
              mandatory true;
              type enumeration {
                enum "deny";
                enum "permit";
              }
            }
            leaf regexp {
              tailf:cli-multi-value;
              tailf:cli-drop-node-name;
              type string;
            }
          }
        }
      }
    }
    container extcommunity-list {
      list expanded {
        tailf:cli-suppress-mode;
        tailf:cli-delete-when-empty;
        key "name regex";
        leaf name {
          type string;
        }
        leaf seq {
          tailf:cli-prefix-key {
            tailf:cli-before-key "2";
          }
          type uint32;
        }
        leaf perm {
          tailf:cli-drop-node-name;
          tailf:cli-prefix-key {
            tailf:cli-before-key "2";
          }
          type enumeration {
            enum "deny";
            enum "permit";
          }
        }
        leaf regex {
          type string;
        }
      }
      list standard {
        tailf:cli-suppress-mode;
        tailf:cli-delete-when-empty;
        key "name spec";
        leaf name {
          type string;
        }
        leaf perm {
          tailf:cli-drop-node-name;
          tailf:cli-prefix-key {
            tailf:cli-before-key "2";
          }
          type enumeration {
            enum "deny";
            enum "permit";
          }
        }
        leaf spec {
          tailf:cli-multi-word-key;
          type string;
        }
      }
    }
    container dhcp {
      leaf relay {
        type boolean;
      }
      container relay-config {
        tailf:cli-drop-node-name;
        container relay {
          container information {
            container option {
              presence "true";
              leaf vpn {
                type empty;
              }
              leaf trust {
                type empty;
              }
            }
            leaf trust-all {
              type empty;
            }
          }
          container sub-option {
            container type {
              leaf cisco {
                type empty;
              }
            }
          }
        }
      }
      leaf snooping {
        type empty;
      }
      container snooping-config {
        tailf:cli-drop-node-name;
        container snooping {
          container information {
            leaf option {
              type empty;
            }
          }
          container verify {
            leaf mac-address {
              type boolean;
            }
          }
          list vlan {
            tailf:cli-suppress-mode;
            tailf:cli-range-list-syntax;
            key "id";
            leaf id {
              type uint16;
            }
          }
        }
      }
      container smart-relay {
        leaf global {
          type empty;
        }
      }
      container packet {
        leaf strict-validation {
          type empty;
        }
      }
    }
    container dns {
      list source-interface {
        tailf:cli-suppress-mode;
        tailf:cli-delete-when-empty;
        key "vrf";
        leaf vrf {
          tailf:cli-expose-key-name;
          type vrf-member-type;
        }
        leaf interface-name {
          tailf:cli-prefix-key;
          tailf:cli-drop-node-name;
          type string;
        }
      }
    }
    container ftp {
      list source-interface {
        tailf:cli-suppress-mode;
        tailf:cli-delete-when-empty;
        key "vrf";
        leaf vrf {
          tailf:cli-expose-key-name;
          type vrf-member-type;
        }
        leaf interface-name {
          tailf:cli-prefix-key;
          tailf:cli-drop-node-name;
          type string;
        }
      }
    }
    container telnet {
      list source-interface {
        tailf:cli-suppress-mode;
        tailf:cli-delete-when-empty;
        key "vrf";
        leaf vrf {
          tailf:cli-expose-key-name;
          type vrf-member-type;
        }
        leaf interface-name {
          tailf:cli-prefix-key;
          tailf:cli-drop-node-name;
          type string;
        }
      }
    }
    container tftp {
      list source-interface {
        tailf:cli-suppress-mode;
        tailf:cli-delete-when-empty;
        key "vrf";
        leaf vrf {
          tailf:cli-expose-key-name;
          type vrf-member-type;
        }
        leaf interface-name {
          tailf:cli-prefix-key;
          tailf:cli-drop-node-name;
          type string;
        }
      }
    }
    container access-list {
      leaf match-local-traffic {
        type empty;
      }
      list list-name {
        tailf:cli-drop-node-name;
        key "id";
        leaf id {
          type string;
        }
        uses ip-access-list-common-grouping;
        list sequence {
          tailf:cli-drop-node-name;
          tailf:cli-suppress-mode;
          tailf:cli-delete-when-empty;
          tailf:cli-compact-syntax;
          tailf:cli-sequence-commands {
            tailf:cli-reset-all-siblings;
          }
          key "id";
          leaf id {
            type uint32;
          }
          leaf action {
            tailf:cli-drop-node-name;
            type enumeration {
              enum "deny";
              enum "permit";
              enum "remark";
            }
          }
          uses ip-access-list-grouping;
          leaf remark-value {
            tailf:cli-multi-value;
            tailf:cli-drop-node-name;
            type string;
          }
        }
      }
    }
    uses ip-grouping {
      augment "multicast" {
        leaf overlay-distributed-dr {
          type empty;
        }
        leaf overlay-spt-only {
          type empty;
        }
      }
    }
    leaf source-route {
      type boolean;
    }
    container source {
      list binding {
        tailf:cli-suppress-mode;
        tailf:cli-delete-when-empty;
        key "address mac vlan";
        leaf address {
          type inet:ipv4-address;
        }
        leaf mac {
          type mac-address-type;
        }
        leaf vlan {
          tailf:cli-expose-key-name;
          type uint16;
        }
        container interface {
          leaf Ethernet {
            tailf:cli-allow-join-with-value;
            type string;
          }
          leaf port-channel {
            tailf:cli-allow-join-with-value;
            type string;
          }
        }
      }
    }
    container igmp {
      container snooping {
        leaf optimise-multicast-flood {
          type boolean;
        }
        leaf vxlan {
          type empty;
        }
        container vxlan-umc {
          choice drop-all-or-some-choice {
            leaf drop {
              type empty;
            }
            container drop-vlan {
              tailf:cli-drop-node-name;
              container drop {
                leaf-list vlan {
                  tailf:cli-range-list-syntax;
                  type uint16;
                }
              }
            }
          }
        }
        container mrouter {
          leaf vpc-peer-link {
            type boolean;
          }
        }
        leaf link-local-groups-suppression {
          type boolean;
        }
        leaf report-suppression {
          type boolean;
        }
        leaf v3-report-suppression {
          type empty;
        }
      }
      container enable-disable-snooping {
        tailf:cli-drop-node-name;
        leaf snooping {
          type boolean;
        }
      }
      leaf flush-routes {
        type empty;
      }
    }
    container nat {
      list pool {
        tailf:cli-suppress-mode;
        tailf:cli-delete-when-empty;
        tailf:cli-compact-syntax;
        tailf:cli-sequence-commands {
          tailf:cli-reset-siblings;
        }
        key "name";
        leaf name {
          type string;
        }
        leaf start-ip {
          tailf:cli-drop-node-name;
          type inet:ipv4-address;
        }
        leaf end-ip {
          tailf:cli-drop-node-name;
          type inet:ipv4-address;
        }
        choice mask-or-len {
          leaf netmask {
            type inet:ipv4-address;
          }
          leaf prefix-length {
            type uint8;
          }
        }
        leaf no-alias {
          type empty;
        }
      }
      container inside {
        container source {
          list list {
            tailf:cli-suppress-mode;
            tailf:cli-delete-when-empty;
            tailf:cli-compact-syntax;
            tailf:cli-sequence-commands;
            key "name interface ifoverload";
            leaf name {
              type string;
            }
            leaf interface {
              tailf:cli-expose-key-name;
              type string;
            }
            leaf vrf {
              tailf:cli-prefix-key {
                tailf:cli-before-key "3";
              }
              tailf:cli-optional-in-sequence;
              type string;
            }
            leaf match-in-vrf {
              tailf:cli-prefix-key {
                tailf:cli-before-key "3";
              }
              tailf:cli-optional-in-sequence;
              type empty;
            }
            leaf ifoverload {
              type enumeration {
                enum "overload";
              }
            }
          }
          container list-pool {
            tailf:cli-drop-node-name;
            list list {
              tailf:cli-suppress-mode;
              tailf:cli-delete-when-empty;
              tailf:cli-compact-syntax;
              tailf:cli-sequence-commands {
                tailf:cli-reset-siblings;
              }
              key "name";
              leaf name {
                type string;
              }
              leaf pool {
                type string;
              }
              leaf vrf {
                tailf:cli-optional-in-sequence;
                type string;
              }
              leaf overload {
                tailf:cli-optional-in-sequence;
                type empty;
              }
              leaf add-route {
                type empty;
              }
            }
          }
          container static {
            list local-map {
              tailf:cli-drop-node-name;
              tailf:cli-suppress-mode;
              key "iaddress gaddress";
              leaf iaddress {
                type inet:ipv4-address;
              }
              leaf gaddress {
                type inet:ipv4-address;
              }
            }
          }
        }
      }
      container outside {
        container source {
          list list {
            tailf:cli-suppress-mode;
            tailf:cli-delete-when-empty;
            tailf:cli-compact-syntax;
            tailf:cli-sequence-commands {
              tailf:cli-reset-siblings;
            }
            key "name pool";
            leaf name {
              type string;
            }
            leaf pool {
              tailf:cli-expose-key-name;
              type string;
            }
            leaf vrf {
              tailf:cli-optional-in-sequence;
              type string;
            }
            leaf add-route {
              type empty;
            }
          }
          container static {
            list local-map {
              tailf:cli-drop-node-name;
              tailf:cli-suppress-mode;
              key "gaddress laddress";
              leaf gaddress {
                type inet:ipv4-address;
              }
              leaf laddress {
                type inet:ipv4-address;
              }
            }
          }
        }
      }
      container translation {
        leaf max-entries {
          type uint16;
        }
        container max-entries-all-host {
          tailf:cli-drop-node-name;
          container max-entries {
            leaf all-host {
              type uint16;
            }
          }
        }
        leaf tcp-timeout {
          type uint32;
        }
        leaf timeout {
          type uint32;
        }
        leaf udp-timeout {
          type uint32;
        }
        leaf sampling-timeout {
          type uint32;
        }
      }
    }
    leaf domain-lookup {
      type boolean;
    }
    list host {
      tailf:cli-suppress-mode;
      tailf:cli-delete-when-empty;
      key "id";
      leaf id {
        type string;
      }
      leaf address {
        tailf:cli-drop-node-name;
        type inet:ipv4-address;
      }
    }
    container prefix-list {
      list prefixes {
        tailf:cli-drop-node-name;
        tailf:cli-suppress-mode;
        tailf:cli-compact-syntax;
        tailf:cli-delete-when-empty;
        key "name";
        leaf name {
          type string;
        }
        leaf description {
          tailf:cli-multi-value;
          tailf:cli-optional-in-sequence;
          type string;
        }
        choice type-choice {
          leaf deny {
            type tailf:ipv4-address-and-prefix-length;
          }
          leaf permit {
            type tailf:ipv4-address-and-prefix-length;
          }
        }
        leaf eq {
          tailf:cli-optional-in-sequence;
          type uint8;
        }
        leaf ge {
          tailf:cli-optional-in-sequence;
          type uint8;
        }
        leaf le {
          type uint8;
        }
        list seq {
          tailf:cli-suppress-mode;
          tailf:cli-delete-when-empty;
          tailf:cli-compact-syntax;
          key "no";
          leaf no {
            type uint32;
          }
          choice type-choice {
            leaf deny {
              type tailf:ipv4-address-and-prefix-length;
            }
            leaf permit {
              type tailf:ipv4-address-and-prefix-length;
            }
          }
          leaf eq {
            tailf:cli-optional-in-sequence;
            type uint8;
          }
          leaf ge {
            tailf:cli-optional-in-sequence;
            type uint8;
          }
          leaf le {
            type uint8;
          }
        }
      }
    }
    container sla {
      list sla-list {
        tailf:cli-drop-node-name;
        key "id";
        leaf id {
          type uint32;
        }

        grouping operation-grouping {
          leaf threshold {
            type uint16;
          }
          leaf timeout {
            type uint32;
          }
          leaf frequency {
            type uint32;
          }
          leaf vrf {
            type vrf-member-type;
          }
        }
        container icmp-echo {
          tailf:cli-add-mode;
          presence "true";
          leaf destination {
            tailf:cli-drop-node-name;
            tailf:cli-hide-in-submode;
            type union {
              type inet:ipv4-address;
              type inet:ipv6-address;
              type string;
            }
          }
          choice iface-or-host {
            leaf source-interface {
              tailf:cli-hide-in-submode;
              type string;
            }
            leaf source-ip {
              tailf:cli-hide-in-submode;
              type union {
                type inet:ipv4-address;
                type inet:ipv6-address;
                type string;
              }
            }
          }
          uses operation-grouping;
          leaf request-data-size {
            type uint16;
          }
          leaf tos {
            type uint8;
          }
          leaf traffic-class {
            type uint8;
          }
        }
        container dns {
          tailf:cli-add-mode;
          presence "true";
          leaf target {
            tailf:cli-drop-node-name;
            tailf:cli-hide-in-submode;
            type string;
          }
          leaf name-server {
            tailf:cli-hide-in-submode;
            type union {
              type inet:ipv4-address;
              type string;
            }
          }
          leaf source-ip {
            tailf:cli-hide-in-submode;
            type union {
              type inet:ipv4-address;
              type string;
            }
          }
          uses operation-grouping;
        }
      }
      list schedule {
        tailf:cli-suppress-mode;
        tailf:cli-delete-when-empty;
        tailf:cli-compact-syntax;
        key "id";
        leaf id {
          type uint32;
        }
        leaf life {
          type union {
            type uint32;
            type enumeration {
              enum "forever";
            }
          }
        }
        container start-time {
          tailf:cli-compact-syntax;
          tailf:cli-flatten-container;
          choice when {
            leaf now {
              type empty;
            }
          }
        }
        leaf ageout {
          type uint32;
        }
        leaf recurring {
          type empty;
        }
      }
      container logging {
        leaf traps {
          type empty;
        }
      }
      list reaction-configuration {
        tailf:cli-suppress-mode;
        tailf:cli-delete-when-empty;
        tailf:cli-compact-syntax;
        tailf:cli-sequence-commands {
          tailf:cli-reset-siblings;
        }
        key "id react";
        leaf id {
          type uint32;
        }
        leaf react {
          tailf:cli-expose-key-name;
          type enumeration {
            enum "connectionLoss";
            enum "rtt";
            enum "timeout";
            enum "verifyError";
          }
        }
        container threshold-value {
          tailf:cli-sequence-commands;
          tailf:cli-compact-syntax;
          tailf:cli-flatten-container;
          tailf:cli-optional-in-sequence;
          leaf upper {
            tailf:cli-drop-node-name;
            type uint16;
          }
          leaf lower {
            tailf:cli-drop-node-name;
            type uint16;
          }
        }
        leaf threshold-type {
          tailf:cli-optional-in-sequence;
          type enumeration {
            enum "average";
            enum "consecutive";
            enum "immediate";
            enum "never";
            enum "xOfy";
          }
        }
        leaf first-arg {
          tailf:cli-drop-node-name;
          tailf:cli-optional-in-sequence;
          type uint8;
        }
        leaf second-arg {
          tailf:cli-drop-node-name;
          type uint8;
        }
        leaf action-type {
          type enumeration {
            enum "none";
            enum "trapAndTrigger";
            enum "trapOnly";
            enum "triggerOnly";
          }
        }
      }
    }
    container tacacs {
      leaf source-interface {
        type string;
      }
    }
    container radius {
      leaf source-interface {
        type string;
      }
    }
    container arp {
      leaf timeout {
        type uint16;
      }
      container inspection {
        leaf-list validate {
          tailf:cli-flat-list-syntax;
          type enumeration {
            enum "dst-mac";
            enum "ip";
            enum "src-mac";
          }
        }
        list vlan {
          tailf:cli-suppress-mode;
          tailf:cli-delete-when-empty;
          tailf:cli-range-list-syntax;
          key "vlan-id";
          leaf vlan-id {
            type uint16;
          }
          container logging {
            leaf dhcp-bindings {
              type enumeration {
                enum "all";
                enum "none";
                enum "permit";
              }
            }
          }
        }
        list filter {
          tailf:cli-suppress-mode;
          tailf:cli-delete-when-empty;
          key "name";
          leaf name {
            type string;
          }
          leaf-list vlan {
            tailf:cli-range-list-syntax;
            type uint16;
          }
        }
      }
    }
    container tcp {
      leaf path-mtu-discovery {
        type empty;
      }
    }
    container ssh {
      list source-interface {
        tailf:cli-suppress-mode;
        tailf:cli-delete-when-empty;
        key "vrf";
        leaf vrf {
          tailf:cli-expose-key-name;
          type vrf-member-type;
        }
        leaf interface-name {
          tailf:cli-prefix-key;
          tailf:cli-drop-node-name;
          type string;
        }
      }
    }
    container http {
      leaf source-interface {
        type string;
      }
    }
    container load-sharing {
      container address {
        tailf:cli-compact-syntax;
        tailf:cli-sequence-commands {
          tailf:cli-reset-siblings;
        }
        leaf address-type {
          tailf:cli-drop-node-name;
          type enumeration {
            enum "destination";
            enum "source";
            enum "source-destination";
          }
        }
        leaf gre {
          tailf:cli-optional-in-sequence;
          type empty;
        }
        leaf gre-outer {
          tailf:cli-optional-in-sequence;
          type empty;
        }
        leaf port {
          tailf:cli-optional-in-sequence;
          type enumeration {
            enum "destination";
            enum "source-destination";
          }
        }
        leaf exclude-l3-proto {
          tailf:cli-optional-in-sequence;
          type empty;
        }
        leaf concatenation {
          tailf:cli-optional-in-sequence;
          type empty;
        }
        leaf rotate {
          type uint8;
        }
        leaf universal-id {
          type uint32;
        }
      }
    }
    container routing {
      container event-history {

        grouping eh-size-leaf {
          leaf size {
            type union {
              type uint32;
              type enumeration {
                enum "disabled";
                enum "large";
                enum "medium";
                enum "small";
              }
            }
          }
        }
        container ufdm {
          uses eh-size-leaf;
        }
        container ufdm-detail {
          uses eh-size-leaf;
        }
        container ufdm-summary {
          uses eh-size-leaf;
        }
        container summary {
          uses eh-size-leaf;
        }
        container recursive-next-hop {
          uses eh-size-leaf;
        }
        container notifications {
          uses eh-size-leaf;
        }
        container modify-route {
          uses eh-size-leaf;
        }
        container loop-detection {
          uses eh-size-leaf;
        }
        container ha {
          uses eh-size-leaf;
        }
        container general {
          uses eh-size-leaf;
        }
        container errors {
          uses eh-size-leaf;
        }
        container detail {
          uses eh-size-leaf;
        }
        container delete-route {
          uses eh-size-leaf;
        }
        container cli {
          uses eh-size-leaf;
        }
        container add-route {
          uses eh-size-leaf;
        }
      }
      leaf download-on-convergence {
        type empty;
      }
    }
    leaf dscp-lop {
      type dscp-value-type;
    }
  }
  container ipv6 {
    container access-list {
      leaf match-local-traffic {
        type empty;
      }
      list list-name {
        tailf:cli-drop-node-name;
        key "id";
        leaf id {
          type string;
        }
        uses ip-access-list-common-grouping;
        list sequence {
          tailf:cli-drop-node-name;
          tailf:cli-suppress-mode;
          tailf:cli-delete-when-empty;
          tailf:cli-sequence-commands {
            tailf:cli-reset-all-siblings;
          }
          tailf:cli-compact-syntax;
          key "id";
          leaf id {
            type uint32;
          }
          leaf action {
            tailf:cli-drop-node-name;
            type enumeration {
              enum "deny";
              enum "permit";
              enum "remark";
            }
          }
          uses ipv6-access-list-grouping;
          leaf remark-value {
            tailf:cli-multi-value;
            tailf:cli-drop-node-name;
            type string;
          }
        }
      }
    }
    leaf adjacency-stale-timer {
      type uint16;
    }
    list host {
      key "name ip";
      leaf name {
        type string;
      }
      leaf ip {
        type inet:ipv6-address;
      }
    }
    uses ipv6-grouping;
    container prefix-list {
      list prefixes {
        tailf:cli-drop-node-name;
        tailf:cli-suppress-mode;
        tailf:cli-delete-when-empty;
        tailf:cli-compact-syntax;
        key "name";
        leaf name {
          type string;
        }
        leaf description {
          tailf:cli-multi-value;
          type string;
        }
        choice type-choice {
          leaf deny {
            type tailf:ipv6-address-and-prefix-length;
          }
          leaf permit {
            type tailf:ipv6-address-and-prefix-length;
          }
        }
        list seq {
          tailf:cli-suppress-mode;
          tailf:cli-delete-when-empty;
          tailf:cli-compact-syntax;
          tailf:cli-sequence-commands {
            tailf:cli-reset-all-siblings;
          }
          key "no";
          leaf no {
            type uint32;
          }
          choice type-choice {
            leaf deny {
              type tailf:ipv6-address-and-prefix-length;
            }
            leaf permit {
              type tailf:ipv6-address-and-prefix-length;
            }
          }
          leaf eq {
            tailf:cli-break-sequence-commands;
            type uint8;
          }
          leaf ge {
            type uint8;
          }
          leaf le {
            type uint8;
          }
        }
      }
    }
    container dhcp {
      leaf relay {
        type boolean;
      }
      container relay-config {
        tailf:cli-drop-node-name;
        container relay {
          container option {
            leaf vpn {
              type empty;
            }
          }
        }
      }
    }
    container switch-packets {
      leaf lla {
        type empty;
      }
    }
    container snooping {
      list policy {
        key "name";
        leaf name {
          type string;
        }
        leaf device-role {
          type enumeration {
            enum "node";
            enum "switch";
          }
        }
        container limit {
          leaf address-count {
            type uint16;
          }
        }
        container protocol {
          leaf dhcp {
            type boolean;
          }
          leaf ndp {
            type boolean;
          }
        }
        leaf security-level {
          type enumeration {
            enum "glean";
            enum "guard";
            enum "inspect";
          }
        }
        container tracking {
          container enable {
            presence "true";
            leaf reachable-lifetime {
              type union {
                type uint32;
                type enumeration {
                  enum "infinite";
                }
              }
            }
          }
        }
        leaf trusted-port {
          type empty;
        }
      }
    }
  }
  container cdp {
    leaf enable {
      type boolean;
    }
    leaf timer {
      type uint8;
    }
    leaf holdtime {
      type uint8;
    }
  }
  container diagnostic {
    container bootup {
      leaf level {
        type enumeration {
          enum "bypass";
          enum "complete";
          enum "extra";
        }
      }
    }
    container monitor {
      container interval {
        list module {
          tailf:cli-suppress-mode;
          tailf:cli-delete-when-empty;
          key "mod";
          leaf mod {
            type uint8;
          }
          list test {
            tailf:cli-suppress-mode;
            tailf:cli-delete-when-empty;
            tailf:cli-compact-syntax;
            tailf:cli-sequence-commands {
              tailf:cli-reset-siblings;
            }
            key "name";
            leaf name {
              type string;
            }
            leaf hour {
              type uint8;
            }
            leaf min {
              type uint8;
            }
            leaf second {
              type uint8;
            }
          }
        }
      }
    }
  }
  container dot1x {
    leaf mac-move {
      type enumeration {
        enum "deny";
        enum "permit";
      }
    }
    leaf radius-accounting {
      type empty;
    }
    leaf system-auth-control {
      type boolean;
    }
  }
  container copp {
    container profile {
      choice profile-choice {
        leaf dense {
          type empty;
        }
        leaf lenient {
          type empty;
        }
        leaf moderate {
          type empty;
        }
        leaf strict {
          type empty;
        }
      }
    }
  }
  uses bfd-grouping {
    augment "bfd" {
      leaf slow-timer {
        type uint16;
      }
      leaf startup-timer {
        type uint8;
      }
      container multihop {
        container interval {
          tailf:cli-compact-syntax;
          tailf:cli-sequence-commands {
            tailf:cli-reset-siblings;
          }
          leaf tx-interval {
            tailf:cli-drop-node-name;
            type uint16;
          }
          leaf min_rx {
            type uint16;
          }
          leaf multiplier {
            type uint8;
          }
        }
      }
    }
  }

  grouping bfd-grouping {
    container bfd {
      uses bfd-content-grouping;
      container ipv4 {
        uses bfd-content-grouping;
      }
      container ipv6 {
        uses bfd-content-grouping;
      }
    }
  }

  grouping bfd-content-grouping {
    leaf echo-rx-interval {
      type uint16;
    }
    container session-interval {
      tailf:cli-sequence-commands;
      tailf:cli-compact-syntax;
      tailf:cli-drop-node-name;
      leaf interval {
        type uint16;
      }
      leaf min_rx {
        type uint16;
      }
      leaf multiplier {
        type uint8;
      }
    }
    leaf echo {
      type boolean;
    }
  }

  container mac {
    container access-list {
      list list-name {
        tailf:cli-drop-node-name;
        key "id";
        leaf id {
          type string;
        }
        container statistics {
          leaf per-entry {
            type empty;
          }
        }
        list sequence {
          tailf:cli-drop-node-name;
          tailf:cli-suppress-mode;
          tailf:cli-delete-when-empty;
          tailf:cli-compact-syntax;
          tailf:cli-sequence-commands;
          key "id";
          leaf id {
            type uint32;
          }
          leaf remark {
            tailf:cli-optional-in-sequence;
            tailf:cli-multi-value;
            type string;
          }
          leaf action {
            tailf:cli-drop-node-name;
            type enumeration {
              enum "deny";
              enum "permit";
            }
          }
          container source {
            tailf:cli-drop-node-name;
            tailf:cli-flatten-container;
            tailf:cli-compact-syntax;
            tailf:cli-sequence-commands;
            choice source-choice {
              leaf any {
                type empty;
              }
              case address {
                leaf address {
                  tailf:cli-drop-node-name;
                  type mac-address-type;
                }
                leaf wildcard-bits {
                  tailf:cli-drop-node-name;
                  type mac-address-type;
                }
              }
            }
          }
          choice destination-choice {
            leaf any {
              type empty;
            }
            case address {
              leaf address {
                tailf:cli-drop-node-name;
                type mac-address-type;
              }
              leaf wildcard-bits {
                tailf:cli-drop-node-name;
                type mac-address-type;
              }
            }
          }
          leaf protocol {
            tailf:cli-drop-node-name;
            tailf:cli-break-sequence-commands;
            type union {
              type enumeration {
                enum "aarp";
                enum "appletalk";
                enum "decnet-iv";
                enum "diagnostic";
                enum "etype-6000";
                enum "etype-8042";
                enum "ip";
                enum "lat";
                enum "lavc-sca";
                enum "mop-console";
                enum "mop-dump";
                enum "vines-echo";
              }
              type string;
            }
          }
          leaf cos {
            type uint8;
          }
          leaf vlan {
            type uint16;
          }
          leaf time-range {
            type uint32;
          }
        }
      }
    }
    container address-table {
      leaf aging-time {
        type uint32;
      }
      container notification {
        leaf mac-move {
          type boolean;
        }
        choice threshold-choice {
          container threshold-enable {
            tailf:cli-drop-node-name;
            leaf threshold {
              type empty;
            }
          }
          container threshold {
            tailf:cli-compact-syntax;
            tailf:cli-sequence-commands {
              tailf:cli-reset-siblings;
            }
            leaf limit {
              type uint8;
            }
            leaf interval {
              type uint16;
            }
          }
        }
      }
      container fabricpath {
        leaf remote-learning {
          type boolean;
        }
      }
      list static {
        tailf:cli-suppress-mode;
        tailf:cli-delete-when-empty;
        key "address vlan";
        leaf address {
          type mac-address-type;
        }
        leaf vlan {
          tailf:cli-expose-key-name;
          type uint16;
        }
        choice drop-or-iface {
          container interface {
            choice eth-or-po {
              leaf Ethernet {
                tailf:cli-allow-join-with-value;
                type string;
              }
              leaf port-channel {
                tailf:cli-allow-join-with-value;
                type string;
              }
            }
          }
          leaf drop {
            type empty;
          }
        }
      }
      list vlan {
        tailf:cli-suppress-mode;
        tailf:cli-delete-when-empty;
        key "id";
        leaf id {
          type uint16;
        }
        container learning {
          leaf mode {
            type string;
          }
        }
      }
      container loop-detect {
        container nve {
          leaf port-down {
            type empty;
          }
        }
        leaf port-down {
          type empty;
        }
      }
    }
  }
  container arp {
    list access-list {
      key "name";
      leaf name {
        type string;
      }
      list sequence {
        tailf:cli-drop-node-name;
        tailf:cli-suppress-mode;
        tailf:cli-delete-when-empty;
        tailf:cli-compact-syntax;
        key "id";
        leaf id {
          type uint32;
        }

        grouping entry-grouping {
          leaf direction {
            tailf:cli-drop-node-name;
            tailf:cli-optional-in-sequence;
            type enumeration {
              enum "request";
              enum "response";
            }
          }
          leaf ip {
            type union {
              type inet:ipv4-address;
              type enumeration {
                enum "any";
                enum "host";
              }
            }
          }
          leaf mask {
            tailf:cli-drop-node-name;
            type inet:ipv4-address;
          }
          leaf host {
            tailf:cli-drop-node-name;
            type inet:ipv4-address;
          }
          leaf resp-ip {
            tailf:cli-drop-node-name;
            type union {
              type inet:ipv4-address;
              type enumeration {
                enum "any";
                enum "host";
              }
            }
          }
          leaf resp-mask {
            tailf:cli-drop-node-name;
            type inet:ipv4-address;
          }
          leaf resp-host {
            tailf:cli-drop-node-name;
            type inet:ipv4-address;
          }
          leaf mac {
            type union {
              type mac-address-type;
              type enumeration {
                enum "any";
                enum "host";
              }
            }
          }
          leaf host-mac {
            tailf:cli-drop-node-name;
            type mac-address-type;
          }
          leaf mac-mask {
            tailf:cli-drop-node-name;
            type mac-address-type;
          }
        }
        leaf remark {
          tailf:cli-multi-value;
          type string;
        }
        container permit {
          tailf:cli-sequence-commands {
            tailf:cli-reset-siblings;
          }
          tailf:cli-compact-syntax;
          uses entry-grouping;
        }
        container deny {
          tailf:cli-sequence-commands {
            tailf:cli-reset-siblings;
          }
          tailf:cli-compact-syntax;
          uses entry-grouping;
        }
      }
    }
  }
  list mac-list {
    tailf:cli-suppress-mode;
    tailf:cli-delete-when-empty;
    key "name";
    leaf name {
      type string;
    }
    list seq {
      tailf:cli-suppress-mode;
      tailf:cli-delete-when-empty;
      tailf:cli-compact-syntax;
      tailf:cli-sequence-commands {
        tailf:cli-reset-siblings;
      }
      key "num";
      leaf num {
        type uint32;
      }
      leaf action {
        tailf:cli-drop-node-name;
        type enumeration {
          enum "deny";
          enum "permit";
        }
      }
      leaf mac-address {
        tailf:cli-drop-node-name;
        type mac-address-type;
      }
      leaf mask {
        tailf:cli-drop-node-name;
        type mac-address-type;
      }
    }
  }
  container macsec {
    list policy {
      key "name";
      leaf name {
        type string;
      }
      leaf cipher-suite {
        type enumeration {
          enum "GCM-AES-128";
          enum "GCM-AES-256";
          enum "GCM-AES-XPN-128";
          enum "GCM-AES-XPN-256";
        }
      }
      leaf conf-offset {
        type enumeration {
          enum "CONF-OFFSET-0";
          enum "CONF-OFFSET-30";
          enum "CONF-OFFSET-50";
        }
      }
      leaf include-icv-indicator {
        type empty;
      }
      leaf include-sci {
        type boolean;
      }
      leaf key-server-priority {
        type uint8;
      }
      leaf sak-expiry-time {
        type uint32;
      }
      leaf security-policy {
        type enumeration {
          enum "must-secure";
          enum "should-secure";
        }
      }
      leaf window-size {
        type uint32;
      }
    }
  }
  container errdisable {
    container recovery {
      container cause {
        leaf bpduguard {
          type empty;
        }
        leaf failed-port-state {
          type empty;
        }
        leaf link-flap {
          type empty;
        }
        leaf loopback {
          type empty;
        }
        leaf psecure-violation {
          type empty;
        }
        leaf security-violation {
          type empty;
        }
        leaf storm-control {
          type empty;
        }
        leaf udld {
          type empty;
        }
        leaf vpc-peerlink {
          type empty;
        }
        leaf pause-rate-limit {
          type empty;
        }
        leaf dcbx-no-ack {
          type empty;
        }
      }
      leaf interval {
        type uint16;
      }
    }
    container detect {
      container cause {
        leaf acl-exception {
          type empty;
        }
        leaf link-flap {
          type empty;
        }
        leaf loopback {
          type empty;
        }
        leaf miscabling {
          type empty;
        }
      }
    }
  }
  list vem {
    key "id";
    leaf id {
      type uint16;
    }
    container host {
      leaf id {
        type string;
      }
      container vmware {
        leaf id {
          type string;
        }
      }
    }
  }
  container vtp {
    leaf mode {
      type enumeration {
        enum "transparent";
        enum "client";
        enum "off";
        enum "server";
      }
    }
    leaf domain {
      type string;
    }
    leaf file {
      type string;
    }
    leaf interface {
      type string;
    }
    leaf password {
      type string;
    }
    leaf pruning {
      type empty;
    }
    leaf version {
      type uint8;
    }
  }
  container telemetry {
    tailf:cli-add-mode;
    presence "true";
    list destination-group {
      key "id";
      leaf id {
        type union {
          type uint16;
          type string;
        }
      }
      list ip {
        tailf:cli-suppress-mode;
        tailf:cli-delete-when-empty;
        tailf:cli-compact-syntax;
        tailf:cli-sequence-commands {
          tailf:cli-reset-siblings;
        }
        key "address port";
        leaf address {
          tailf:cli-expose-key-name;
          type inet:ipv4-address;
        }
        leaf port {
          tailf:cli-expose-key-name;
          type uint16;
        }
        leaf protocol {
          type enumeration {
            enum "HTTP";
            enum "TCP";
            enum "UDP";
            enum "gRPC";
          }
        }
        leaf encoding {
          type enumeration {
            enum "GPB";
            enum "JSON";
            enum "Form-data";
            enum "GPB-compact";
            enum "XML";
          }
        }
      }
      leaf use-vrf {
        type string;
      }
      container use-chunking {
        leaf size {
          type uint16;
        }
      }
      leaf use-compression {
        type enumeration {
          enum "gzip";
        }
      }
    }
    container destination-profile {
      tailf:cli-add-mode;
      presence "true";
      leaf source-interface {
        type string;
      }
      leaf use-compression {
        type enumeration {
          enum "gzip";
        }
      }
      leaf use-nodeid {
        type string;
      }
      container use-retry {
        leaf size {
          type uint16;
        }
      }
      leaf use-vrf {
        type string;
      }
    }
    list sensor-group {
      key "id";
      leaf id {
        type union {
          type uint16;
          type string;
        }
      }
      leaf data-source {
        type enumeration {
          enum "DME";
          enum "NX-API";
          enum "NATIVE";
          enum "YANG";
        }
      }
      list path {
        tailf:cli-suppress-mode;
        tailf:cli-delete-when-empty;
        tailf:cli-compact-syntax;
        key "dn";
        leaf dn {
          type union {
            type enumeration {
              enum "adjacency";
              enum "environment";
              enum "interface";
              enum "mac";
              enum "mac-all";
              enum "resources";
              enum "rib";
              enum "vxlan";
            }
            type string;
          }
        }
        leaf depth {
          type union {
            type uint8;
            type enumeration {
              enum "unbounded";
            }
          }
        }
        leaf query-condition {
          type string;
        }
        leaf filter-condition {
          type string;
        }
        leaf alias {
          type string;
        }
      }
    }
    list subscription {
      key "id";
      leaf id {
        type uint16;
      }
      list dst-grp {
        tailf:cli-suppress-mode;
        key "id";
        leaf id {
          type union {
            type uint16;
            type string;
          }
        }
      }
      list snsr-grp {
        tailf:cli-suppress-mode;
        tailf:cli-delete-when-empty;
        tailf:cli-compact-syntax;
        key "id";
        leaf id {
          type union {
            type uint16;
            type string;
          }
        }
        leaf sample-interval {
          type uint32;
        }
      }
    }
  }
  container icam {
    container monitor {
      leaf scale {
        type empty;
      }
      container scale-config {
        tailf:cli-drop-node-name;
        container scale {

          grouping limit-leaf {
            leaf limit {
              type uint32;
            }
          }
          container l2-switching {
            container infra {
              container mac {
                uses limit-leaf;
              }
            }
            container stp {
              container isolated-portvlan {
                uses limit-leaf;
              }
              container mst-instance {
                uses limit-leaf;
              }
              container mst-vport {
                uses limit-leaf;
              }
              container rpvst-vlan {
                uses limit-leaf;
              }
              container rpvst-vport {
                uses limit-leaf;
              }
            }
            container vlan {
              container vlan-count {
                uses limit-leaf;
              }
            }
          }
          container multicast-routing {
            container pim {
              container neighbor {
                uses limit-leaf;
              }
            }
            container routing-forwarding {
              container route-sg-v4 {
                uses limit-leaf;
              }
              container route-sg-v6 {
                uses limit-leaf;
              }
              container route-starg-v4 {
                uses limit-leaf;
              }
              container route-starg-v6 {
                uses limit-leaf;
              }
              container route-v4 {
                uses limit-leaf;
              }
              container route-v6 {
                uses limit-leaf;
              }
            }
          }
          container threshold {
            tailf:cli-sequence-commands {
              tailf:cli-reset-siblings;
            }
            tailf:cli-compact-syntax;
            leaf info {
              type uint8;
            }
            leaf warning {
              type uint8;
            }
            leaf critical {
              type uint8;
            }
          }
          container unicast-routing {
            container arp {
              container arp-count {
                uses limit-leaf;
              }
            }
            container bfd {
              container session {
                uses limit-leaf;
              }
            }
            container bgp {
              container neighbor {
                uses limit-leaf;
              }
            }
            container eigrp {
              container neighbor {
                uses limit-leaf;
              }
              container route {
                uses limit-leaf;
              }
            }
            container hsrp {
              container mac {
                uses limit-leaf;
              }
            }
            container ipv6-nd {
              container nd-count {
                uses limit-leaf;
              }
            }
            container isis {
              container adjacency {
                uses limit-leaf;
              }
              container bfd-session {
                uses limit-leaf;
              }
              container route {
                uses limit-leaf;
              }
            }
            container ospf {
              container area {
                uses limit-leaf;
              }
              container lsa {
                uses limit-leaf;
              }
              container neighbor {
                uses limit-leaf;
              }
            }
            container pbr {
              container ace-v4 {
                uses limit-leaf;
              }
              container ace-v6 {
                uses limit-leaf;
              }
              container intf {
                uses limit-leaf;
              }
              container nh-per-policy {
                uses limit-leaf;
              }
              container seq-per-policy {
                uses limit-leaf;
              }
            }
            container routing {
              container host-route-v4 {
                uses limit-leaf;
              }
              container host-route-v6 {
                uses limit-leaf;
              }
              container lpm-route-v4 {
                uses limit-leaf;
              }
              container lpm-route-v6 {
                uses limit-leaf;
              }
            }
            container vrf {
              container vrf-count {
                uses limit-leaf;
              }
            }
            container vrrp {
              container grp-per-intf {
                uses limit-leaf;
              }
            }
            container vrrp3 {
              container grp-and-path {
                uses limit-leaf;
              }
              container grp-dft-timer {
                uses limit-leaf;
              }
              container grp-per-intf {
                uses limit-leaf;
              }
              container grp-relax-timer {
                uses limit-leaf;
              }
              container path-dft-timer {
                uses limit-leaf;
              }
            }
          }
          container vxlan {

            grouping vxlan-common-limits {
              container vlan-logical-port-vp {
                uses limit-leaf;
              }
              container vlan-per-fex-port {
                uses limit-leaf;
              }
              container vni {
                uses limit-leaf;
              }
              container vrf {
                uses limit-leaf;
              }
              container vtep {
                uses limit-leaf;
              }
            }

            grouping vxlan-bgp-common-limits {
              container host-route-v4 {
                uses limit-leaf;
              }
              container host-route-v6 {
                uses limit-leaf;
              }
              container igmp-group {
                uses limit-leaf;
              }
              container mac {
                uses limit-leaf;
              }
              container overlay-lpm-route-v4 {
                uses limit-leaf;
              }
              container overlay-lpm-route-v6 {
                uses limit-leaf;
              }
              container svi {
                uses limit-leaf;
              }
            }
            container bgp {
              uses vxlan-bgp-common-limits;
              container underlay-mcast-group;
              uses vxlan-common-limits;
            }
            container bgp-ir {
              uses vxlan-bgp-common-limits;
              uses vxlan-common-limits;
            }
            container fl {
              container igmp-group {
                uses limit-leaf;
              }
              container ir-mac {
                uses limit-leaf;
              }
              container ir-peer {
                uses limit-leaf;
              }
              container ir-vni {
                uses limit-leaf;
              }
              container static-mac-to-vtep {
                uses limit-leaf;
              }
              container total-mac {
                uses limit-leaf;
              }
              container underlay-mcast-group {
                uses limit-leaf;
              }
              uses vxlan-common-limits;
            }
          }
        }
      }
    }
  }
  container crypto {
    container key {
      container param {
        list rsa {
          tailf:cli-suppress-mode;
          tailf:cli-delete-when-empty;
          tailf:cli-compact-syntax;
          tailf:cli-sequence-commands {
            tailf:cli-reset-siblings;
          }
          key "label";
          leaf label {
            tailf:cli-expose-key-name;
            type string;
          }
          leaf modulus {
            type uint16;
          }
          leaf exportable {
            type empty;
          }
        }
      }
      container generate {
        list rsa {
          tailf:cli-suppress-mode;
          tailf:cli-delete-when-empty;
          tailf:cli-compact-syntax;
          tailf:cli-sequence-commands {
            tailf:cli-reset-siblings;
          }
          key "label";
          leaf label {
            tailf:cli-expose-key-name;
            type string;
          }
          leaf exportable {
            tailf:cli-optional-in-sequence;
            type empty;
          }
          leaf modulus {
            type uint16;
          }
        }
      }
    }
    list certificatemap {
      key "mapname";
      leaf mapname {
        tailf:cli-expose-key-name;
        type string;
      }
      container filter {
        leaf altname-email {
          type string;
        }
        leaf altname-upn {
          type string;
        }
        leaf subject-name {
          type string;
        }
      }
    }
    container cert {
      list ssh-authorize {
        tailf:cli-suppress-mode;
        tailf:cli-delete-when-empty;
        tailf:cli-compact-syntax;
        tailf:cli-sequence-commands {
          tailf:cli-reset-siblings;
        }
        key "name";
        leaf name {
          type string;
        }
        leaf map {
          type string;
        }
        leaf map2 {
          tailf:cli-drop-node-name;
          type string;
        }
      }
    }
    container ca {
      leaf lookup {
        type enumeration {
          enum "both";
          enum "local";
          enum "remote";
        }
      }
      list trustpoint {
        key "label";
        leaf label {
          type string;
        }
        container enrollment {
          leaf terminal {
            type empty;
          }
        }
        container revocation-check {
          tailf:cli-compact-syntax;
          tailf:cli-sequence-commands {
            tailf:cli-reset-siblings;
          }
          leaf crl {
            tailf:cli-optional-in-sequence;
            type empty;
          }
          leaf ocsp {
            tailf:cli-optional-in-sequence;
            type empty;
          }
          leaf none {
            type empty;
          }
        }
        leaf rsakeypair {
          type string;
        }
      }
    }
  }
  list time-range {
    key "name";
    leaf name {
      type string;
    }
  }
  container snmp-server {
    leaf contact {
      tailf:cli-multi-value;
      type string;
    }
    container disable {
      container snmp-aaa {
        leaf sync {
          type empty;
        }
      }
    }
    list community {
      tailf:cli-suppress-mode;
      tailf:cli-delete-when-empty;
      key "snmp-community-string";
      leaf snmp-community-string {
        type word32;
      }
      leaf group {
        type word32;
      }
      leaf use-acl {
        type word32;
      }
    }
    container community-config {
      tailf:cli-drop-node-name;
      list community {
        tailf:cli-suppress-mode;
        tailf:cli-delete-when-empty;
        tailf:cli-compact-syntax;
        key "snmp-community-string";
        leaf snmp-community-string {
          type string;
        }
        leaf use-ipv4acl {
          type string;
        }
        leaf use-ipv6acl {
          type string;
        }
      }
    }
    container counter {
      container cache {
        leaf enable {
          type boolean;
        }
        leaf timeout {
          type uint16;
        }
      }
    }
    container enable {
      container traps {
        container aaa {
          leaf server-state-change {
            type empty;
          }
        }
        container bfd {
          leaf session-down {
            type boolean;
          }
          leaf session-up {
            type boolean;
          }
        }
        choice bgp-choice {
          leaf bgp {
            type empty;
          }
          container bgp-state-chg {
            tailf:cli-drop-node-name;
            container bgp {
              leaf state-changes {
                type empty;
              }
              container state-changes-alt {
                tailf:cli-drop-node-name;
                container state-changes {
                  leaf all {
                    type empty;
                  }
                  leaf backward-trans {
                    type empty;
                  }
                  leaf limited {
                    type empty;
                  }
                }
              }
            }
          }
        }
        container bgp-threshold {
          tailf:cli-drop-node-name;
          container bgp {
            container threshold {
              leaf prefix {
                type empty;
              }
            }
          }
        }
        container bgp-cbgp2 {
          tailf:cli-drop-node-name;
          container bgp {
            leaf cbgp2 {
              type empty;
            }
          }
        }
        container bridge {
          leaf newroot {
            type empty;
          }
          leaf topologychange {
            type empty;
          }
        }
        container config {
          leaf ccmCLIRunningConfigChanged {
            type empty;
          }
        }
        container callhome {
          leaf event-notify {
            type empty;
          }
          leaf smtp-send-fail {
            type empty;
          }
        }
        container cfs {
          leaf state-change-notif {
            type empty;
          }
          leaf merge-failure {
            type empty;
          }
        }
        container entity {
          leaf entity_mib_change {
            type boolean;
          }
          leaf entity_module_status_change {
            type boolean;
          }
          leaf entity_power_status_change {
            type boolean;
          }
          leaf entity_module_inserted {
            type boolean;
          }
          leaf entity_module_removed {
            type boolean;
          }
          leaf entity_unrecognised_module {
            type boolean;
          }
          leaf entity_fan_status_change {
            type boolean;
          }
          leaf entity_power_out_change {
            type boolean;
          }
          leaf entity_sensor {
            type boolean;
          }
          leaf cefcMIBEnableStatusNotification {
            type boolean;
          }
          leaf cefcEnablePSOutputChangeNotif {
            type boolean;
          }
        }
        container feature-control {
          leaf FeatureOpStatusChange {
            type empty;
          }
          leaf ciscoFeatOpStatusChange {
            type empty;
          }
        }
        container generic {
          leaf coldStart {
            type boolean;
          }
          leaf warmStart {
            type boolean;
          }
        }
        container hsrp {
          leaf state-change {
            type empty;
          }
        }
        container ip {
          leaf sla {
            type empty;
          }
        }
        container license {
          leaf notify-license-expiry {
            type boolean;
          }
          leaf notify-license-expiry-warning {
            type boolean;
          }
          leaf notify-licensefile-missing {
            type boolean;
          }
          leaf notify-no-license-for-feature {
            type boolean;
          }
        }
        container link {
          leaf cisco-xcvr-mon-status-chg {
            type empty;
          }
          leaf cieLinkDown {
            type boolean;
          }
          leaf cieLinkUp {
            type boolean;
          }
          leaf delayed-link-state-change {
            type boolean;
          }
          leaf extended-linkDown {
            type boolean;
          }
          leaf extended-linkUp {
            type boolean;
          }
          leaf linkDown {
            type boolean;
          }
          leaf linkUp {
            type boolean;
          }
          leaf connUnitPortStatusChange {
            type boolean;
          }
          leaf cErrDisableInterfaceEventRev1 {
            type boolean;
          }
          leaf cmn-mac-move-notification {
            type boolean;
          }
        }
        container old-link-syntax {
          tailf:cli-drop-node-name;
          leaf link {
            type empty;
          }
        }
        container mmode {
          leaf cseMaintModeChangeNotify {
            type empty;
          }
          leaf cseNormalModeChangeNotify {
            type empty;
          }
        }
        container mpls {
          container ldp {
            leaf session-up {
              type boolean;
            }
            leaf session-down {
              type boolean;
            }
          }
        }
        container pim {
          leaf pimNeighborLoss {
            type empty;
          }
        }
        container pseudowire {
          container vc {
            leaf up {
              type boolean;
            }
            leaf down {
              type boolean;
            }
          }
        }
        container port-security {
          leaf access-secure-mac-violation {
            type boolean;
          }
          leaf trunk-secure-mac-violation {
            type boolean;
          }
        }
        container lldp {
          leaf lldpRemTablesChange {
            type empty;
          }
        }
        container ospf {
          presence "true";
          leaf proc-tag {
            tailf:cli-drop-node-name;
            type string;
          }
        }
        container ospfv3 {
          presence "true";
          leaf lsa {
            type boolean;
          }
          leaf proc-tag {
            tailf:cli-drop-node-name;
            type string;
          }
          container rate-limit {
            tailf:cli-compact-syntax;
            tailf:cli-sequence-commands {
              tailf:cli-reset-siblings;
            }
            leaf window-size {
              tailf:cli-drop-node-name;
              type uint8;
            }
            leaf num-traps {
              tailf:cli-drop-node-name;
              type uint8;
            }
          }
        }
        container poe {
          leaf portonoff {
            type empty;
          }
          leaf pwrusageon {
            type empty;
          }
          leaf pwrusageoff {
            type empty;
          }
          leaf police {
            type empty;
          }
        }
        container rf {
          leaf redundancy_framework {
            type boolean;
          }
        }
        container rmon {
          leaf fallingAlarm {
            type boolean;
          }
          leaf hcFallingAlarm {
            type boolean;
          }
          leaf hcRisingAlarm {
            type boolean;
          }
          leaf risingAlarm {
            type boolean;
          }
        }
        container snmp {
          leaf authentication {
            type empty;
          }
        }
        container storm-control-enable {
          tailf:cli-drop-node-name;
          leaf storm-control {
            type boolean;
          }
        }
        container storm-control {
          leaf trap-rate {
            type uint16;
          }
          leaf cpscEventRev1 {
            type boolean;
          }
        }
        container stpx {
          leaf inconsistency {
            type empty;
          }
          leaf root-inconsistency {
            type empty;
          }
          leaf loop-inconsistency {
            type empty;
          }
        }
        container syslog {
          leaf message-generated {
            type empty;
          }
        }
        container sysmgr {
          leaf cseFailSwCoreNotifyExtended {
            type empty;
          }
        }
        container system {
          leaf Clock-change-notification {
            type empty;
          }
        }
        container upgrade {
          leaf UpgradeOpNotifyOnCompletion {
            type boolean;
          }
          leaf UpgradeJobStatusNotify {
            type boolean;
          }
        }
        container vtp {
          leaf notifs {
            type empty;
          }
          leaf vlancreate {
            type empty;
          }
          leaf vlandelete {
            type empty;
          }
        }
        container zone {
          leaf default-zone-behavior-change {
            type empty;
          }
          leaf enhanced-zone-db-change {
            type empty;
          }
          leaf merge-failure {
            type empty;
          }
          leaf merge-success {
            type empty;
          }
          leaf request-reject1 {
            type empty;
          }
          leaf unsupp-mem {
            type empty;
          }
        }
      }
      leaf all-traps {
        type empty;
      }
    }
    leaf location {
      tailf:cli-multi-value;
      type string;
    }
    container source-interface {
      leaf informs {
        type string;
      }
      leaf inform {
        type string;
      }
      leaf traps {
        type string;
      }
      leaf trap {
        type string;
      }
    }
    list user {
      tailf:cli-suppress-mode;
      tailf:cli-delete-when-empty;
      tailf:cli-compact-syntax;
      tailf:cli-sequence-commands {
        tailf:cli-reset-siblings;
      }
      key "name";
      leaf name {
        type string;
      }
      leaf role {
        tailf:cli-drop-node-name;
        tailf:cli-optional-in-sequence;
        type user-role-type;
      }
      leaf pwd_type {
        tailf:cli-optional-in-sequence;
        type enumeration {
          enum "6";
        }
      }
      container auth {
        tailf:cli-compact-syntax;
        tailf:cli-flatten-container;
        tailf:cli-sequence-commands {
          tailf:cli-reset-siblings;
        }
        choice auth-alg {
          leaf md5 {
            type string;
          }
          leaf sha {
            type string;
          }
          leaf sha-224 {
            type string;
          }
          leaf sha-256 {
            type string;
          }
          leaf sha-384 {
            type string;
          }
          leaf sha-512 {
            type string;
          }
        }
        container priv {
          tailf:cli-break-sequence-commands;
          tailf:cli-compact-syntax;
          tailf:cli-flatten-container;
          choice priv-choice {
            leaf passphrase-2 {
              tailf:cli-drop-node-name;
              type string;
            }
            leaf des {
              type string;
            }
            leaf aes-128 {
              type string;
            }
          }
        }
        leaf localizedkeyAlt {
          tailf:alt-name "localizedkey";
          type empty;
        }
        leaf engineID {
          type string;
        }
        leaf localizedkey {
          type empty;
        }
        leaf localizedV2key {
          type empty;
        }
      }
    }
    container user-secondary-roles {
      tailf:cli-drop-node-name;
      list user {
        tailf:cli-suppress-mode;
        tailf:cli-delete-when-empty;
        key "name role";
        leaf name {
          type string;
        }
        leaf role {
          type user-role-type;
        }
      }
    }
    container user-config {
      tailf:cli-drop-node-name;
      list user {
        tailf:cli-suppress-mode;
        tailf:cli-delete-when-empty;
        tailf:cli-compact-syntax;
        key "name";
        leaf name {
          type string;
        }
        leaf use-ipv4acl {
          type string;
        }
        leaf use-ipv6acl {
          type string;
        }
      }
    }
    container user-config2 {
      tailf:cli-drop-node-name;
      list user {
        tailf:cli-suppress-mode;
        tailf:cli-delete-when-empty;
        key "name";
        leaf name {
          type string;
        }
        leaf enforcePriv {
          type empty;
        }
      }
    }
    list host {
      tailf:cli-suppress-mode;
      tailf:cli-delete-when-empty;
      tailf:cli-compact-syntax;
      tailf:cli-sequence-commands {
        tailf:cli-reset-siblings;
      }
      key "host-id udp-port";
      leaf host-id {
        type string;
      }
      leaf udp-port {
        tailf:cli-expose-key-name;
        type uint16;
      }
      leaf type {
        tailf:cli-drop-node-name;
        tailf:cli-prefix-key {
          tailf:cli-before-key "2";
        }
        type enumeration {
          enum "traps";
          enum "informs";
        }
      }
      leaf version {
        tailf:cli-prefix-key {
          tailf:cli-before-key "2";
        }
        type enumeration {
          enum "1";
          enum "2c";
          enum "3";
        }
      }
      leaf security-level {
        tailf:cli-drop-node-name;
        tailf:cli-optional-in-sequence;
        tailf:cli-prefix-key {
          tailf:cli-before-key "2";
        }
        type enumeration {
          enum "auth";
          enum "priv";
        }
      }
      leaf id {
        tailf:cli-drop-node-name;
        tailf:cli-prefix-key {
          tailf:cli-before-key "2";
        }
        type string;
      }
    }
    container snmp-server-host-vrf {
      tailf:cli-drop-node-name;
      list host {
        tailf:cli-suppress-mode;
        tailf:cli-delete-when-empty;
        tailf:cli-sequence-commands;
        tailf:cli-compact-syntax;
        key "host-id udp-port";
        leaf host-id {
          type string;
        }
        leaf udp-port {
          tailf:cli-expose-key-name;
          type uint16;
        }
        leaf use-vrf {
          tailf:cli-prefix-key {
            tailf:cli-before-key "2";
          }
          type string;
        }
      }
    }
    container snmp-server-host-src-iface {
      tailf:cli-drop-node-name;
      list host {
        tailf:cli-suppress-mode;
        tailf:cli-delete-when-empty;
        tailf:cli-sequence-commands;
        tailf:cli-compact-syntax;
        key "host-id udp-port";
        leaf host-id {
          type string;
        }
        leaf udp-port {
          tailf:cli-expose-key-name;
          type uint16;
        }
        leaf source-interface {
          tailf:cli-prefix-key {
            tailf:cli-before-key "2";
          }
          type string;
        }
      }
    }
    list context {
      tailf:cli-suppress-mode;
      tailf:cli-delete-when-empty;
      tailf:cli-compact-syntax;
      key "name";
      leaf name {
        type string;
      }
      leaf instance {
        type string;
      }
      leaf vrf {
        type string;
      }
      leaf topology {
        type string;
      }
    }
    container mib {
      list community-map {
        tailf:cli-suppress-mode;
        tailf:cli-delete-when-empty;
        key "community";
        leaf community {
          type word32;
        }
        leaf context {
          type string;
        }
      }
    }
    leaf globalEnforcePriv {
      type empty;
    }
    leaf packetsize {
      type uint16;
    }
    container engineID {
      leaf local {
        type string;
      }
    }
    container aaa-user {
      leaf cache-timeout {
        type uint32;
      }
    }
  }
  container callhome {
    tailf:cli-add-mode;
    leaf contract-id {
      type string;
    }
    leaf customer-id {
      tailf:cli-multi-value;
      type string;
    }
    leaf email-contact {
      type string;
    }
    leaf phone-contact {
      type string;
    }
    leaf streetaddress {
      tailf:cli-multi-value;
      type string;
    }
    list destination-profile {
      tailf:cli-suppress-mode;
      tailf:cli-delete-when-empty;
      key "name";
      leaf name {
        type string;
      }
      leaf format {
        type enumeration {
          enum "XML";
          enum "full-txt";
          enum "short-txt";
        }
      }
      leaf transport-method {
        type enumeration {
          enum "email";
          enum "http";
        }
      }
      leaf message-size {
        type uint32;
      }
      list index {
        tailf:cli-suppress-mode;
        tailf:cli-delete-when-empty;
        key "id";
        leaf id {
          type uint8;
        }
        leaf email-addr {
          type string;
        }
        leaf http {
          type string;
        }
      }
    }
    container transport {
      container http {
        leaf use-vrf {
          type string;
        }
      }
    }
    leaf enable {
      type empty;
    }
  }
  container snmp {
    container ifmib {
      container ifalias {
        leaf long {
          type empty;
        }
      }
    }
  }
  container rmon {
    list event {
      tailf:cli-compact-syntax;
      tailf:cli-suppress-mode;
      tailf:cli-delete-when-empty;
      key "number";
      leaf number {
        type uint16;
      }
      leaf log {
        type empty;
      }
      leaf trap {
        type string;
      }
      leaf description {
        type string;
      }
      leaf owner {
        type string;
      }
    }
    list alarm {
      tailf:cli-suppress-mode;
      tailf:cli-delete-when-empty;
      tailf:cli-compact-syntax;
      tailf:cli-sequence-commands {
        tailf:cli-reset-siblings;
      }
      key "number";
      leaf number {
        type uint16;
      }
      leaf mib {
        tailf:cli-drop-node-name;
        type string;
      }
      leaf sample-interval {
        tailf:cli-drop-node-name;
        type uint32;
      }
      leaf sample-mode {
        tailf:cli-drop-node-name;
        type enumeration {
          enum "absolute";
          enum "delta";
        }
      }
      leaf rising-threshold {
        type int64;
      }
      leaf event-to-fire-rising {
        tailf:cli-drop-node-name;
        tailf:cli-optional-in-sequence;
        type uint16;
      }
      leaf falling-threshold {
        type int64;
      }
      leaf event-to-fire-falling {
        tailf:cli-drop-node-name;
        tailf:cli-optional-in-sequence;
        type uint16;
      }
      leaf owner {
        type string;
      }
    }
  }
  container install {
    container feature-set {
      uses feature-set-grouping;
    }
  }
  container feature-set {
    uses feature-set-grouping {
      refine "mpls";
    }
  }
  list fex {
    key "id";
    leaf id {
      type uint8;
    }
    container pinning {
      leaf max-links {
        type uint16;
      }
    }
    leaf description {
      tailf:cli-multi-value;
      type string;
    }
    leaf serial {
      type string;
    }
    leaf type {
      type string;
    }
    container locator-led {
      leaf fex {
        type uint8;
      }
    }
    list hardware {
      tailf:cli-suppress-mode;
      tailf:cli-delete-when-empty;
      key "module";
      leaf module {
        type union {
          type string;
          type enumeration {
            enum "N2148T";
            enum "N2224TP";
            enum "N2232P";
            enum "N2232TM";
            enum "N2232TM-E";
            enum "N2248PQ";
            enum "N2248T";
            enum "N2248TP-E";
            enum "N2332TQ";
            enum "N2348PQ";
            enum "N2348TQ";
            enum "N2348UPQ";
            enum "NB22DELL";
            enum "NB22FJ";
            enum "NB22HP";
            enum "NB22IBM";
          }
        }
      }
      leaf buffer-threshold {
        type uint32;
      }
      leaf queue-limit {
        type uint32;
      }
      leaf shared-buffer-size {
        type uint32;
      }
      container uplink-pause-no-drop {
        leaf distance {
          type uint32;
        }
      }
      leaf qos-policy-offload {
        type empty;
      }
    }
  }
  container mpls {
    container label {
      container range {
        tailf:cli-compact-syntax;
        tailf:cli-sequence-commands {
          tailf:cli-reset-siblings;
        }
        leaf min {
          tailf:cli-drop-node-name;
          type uint32;
        }
        leaf max {
          tailf:cli-drop-node-name;
          type uint32;
        }
      }
    }
    container ldp {
      container configuration {
        tailf:cli-add-mode;
        leaf advertise-labels {
          type boolean;
        }
        container advertise-labels-config {
          tailf:cli-drop-node-name;
          container advertise-labels {
            list for {
              tailf:cli-suppress-mode;
              tailf:cli-delete-when-empty;
              key "name";
              leaf name {
                type string;
              }
              leaf to {
                type string;
              }
            }
            list interface {
              tailf:cli-suppress-mode;
              tailf:cli-delete-when-empty;
              key "name";
              leaf name {
                type string;
              }
            }
          }
        }
        container backoff {
          tailf:cli-compact-syntax;
          tailf:cli-sequence-commands {
            tailf:cli-reset-siblings;
          }
          leaf initial {
            tailf:cli-drop-node-name;
            type uint32;
          }
          leaf maximum {
            tailf:cli-drop-node-name;
            type uint32;
          }
        }
        container discovery {
          container hello {
            leaf holdtime {
              type uint16;
            }
            leaf interval {
              type uint16;
            }
          }
          container targeted-hello {
            container accept {
              presence "true";
              leaf from {
                type string;
              }
            }
            leaf holdtime {
              type uint16;
            }
            leaf interval {
              type uint16;
            }
          }
        }
        container explicit-null {
          tailf:cli-compact-syntax;
          tailf:cli-sequence-commands {
            tailf:cli-reset-siblings;
          }
          presence "true";
          leaf for {
            tailf:cli-optional-in-sequence;
            type string;
          }
          leaf to {
            type string;
          }
        }
        leaf graceful-restart {
          type boolean;
        }
        container gracefule-restart-config {
          tailf:cli-drop-node-name;
          container graceful-restart {
            container timers {
              leaf forwarding-holding {
                type uint16;
              }
              leaf max-recovery {
                type uint16;
              }
              leaf neighbor-liveness {
                type uint16;
              }
            }
          }
        }
        leaf holdtime {
          type union {
            type uint16;
            type enumeration {
              enum "infinite";
            }
          }
        }
        container label {
          container allocate {
            container global {
              choice instance-choice {
                leaf all-routes {
                  type empty;
                }
                leaf host-routes {
                  type empty;
                }
                leaf prefix-list {
                  type string;
                }
              }
            }
          }
        }
        container logging {
          leaf neighbor-changes {
            type boolean;
          }
          container password {
            choice configuration-choice {
              leaf configuration {
                type boolean;
              }
              container configuration-rate-limit {
                tailf:cli-drop-node-name;
                container configuration {
                  leaf rate-limit {
                    type uint8;
                  }
                }
              }
            }
            choice rollover-choice {
              leaf rollover {
                type boolean;
              }
              container rollover-rate-limit {
                tailf:cli-drop-node-name;
                container rollover {
                  leaf rate-limit {
                    type uint8;
                  }
                }
              }
            }
          }
        }
        container mpls {
          container ip {
            leaf default-route {
              type empty;
            }
          }
        }
        list neighbor {
          tailf:cli-suppress-mode;
          tailf:cli-delete-when-empty;
          key "address";
          leaf address {
            type inet:ipv4-address;
          }
          leaf implicit-withdraw {
            type empty;
          }
          container labels {
            leaf accept {
              type string;
            }
          }
          leaf targeted {
            type empty;
          }
        }
        container password {
          container fallback {
            leaf key-chain {
              type string;
            }
          }
          list option {
            tailf:cli-suppress-mode;
            tailf:cli-delete-when-empty;
            tailf:cli-compact-syntax;
            tailf:cli-sequence-commands {
              tailf:cli-reset-siblings;
            }
            key "sequence";
            leaf sequence {
              type uint16;
            }
            leaf for {
              type string;
            }
            leaf key-chain {
              type string;
            }
          }
          container required {
            presence "true";
            leaf for {
              type string;
            }
          }
        }
        choice mpls-ldp-router-id-choice {
          leaf router-id {
            type string;
          }
          container router-id-force {
            tailf:cli-drop-node-name;
            tailf:cli-compact-syntax;
            tailf:cli-sequence-commands;
            leaf router-id {
              type string;
            }
            leaf force {
              type empty;
            }
          }
        }
        container session {
          container protection {
            presence "true";
            tailf:cli-sequence-commands {
              tailf:cli-reset-siblings;
            }
            tailf:cli-compact-syntax;
            leaf for {
              tailf:cli-optional-in-sequence;
              type string;
            }
            leaf duration {
              type union {
                type uint32;
                type enumeration {
                  enum "infinite";
                }
              }
            }
          }
        }
        leaf shutdown {
          type boolean;
        }
      }
    }
  }
  container segment-routing {
    tailf:cli-add-mode;
    container mpls {
      tailf:cli-add-mode;
      container global-block {
        tailf:cli-compact-syntax;
        tailf:cli-sequence-commands {
          tailf:cli-reset-siblings;
        }
        leaf min {
          tailf:cli-drop-node-name;
          type uint32;
        }
        leaf max {
          tailf:cli-drop-node-name;
          type uint32;
        }
      }
      container connected-prefix-sid-map {
        tailf:cli-add-mode;
        presence "true";
        container address-family {
          container ipv4 {
            tailf:cli-add-mode;
            presence "true";
            list prefix-format {
              tailf:cli-drop-node-name;
              tailf:cli-suppress-mode;
              tailf:cli-delete-when-empty;
              tailf:cli-compact-syntax;
              tailf:cli-sequence-commands {
                tailf:cli-reset-siblings;
              }
              key "address";
              leaf address {
                type inet:ipv4-prefix;
              }
              leaf type {
                tailf:cli-drop-node-name;
                type enumeration {
                  enum "absolute";
                  enum "index";
                }
              }
              leaf start {
                tailf:cli-drop-node-name;
                type uint32;
              }
            }
          }
        }
      }
    }
  }
  container vlan {
    list vlan-list {
      tailf:cli-drop-node-name;
      tailf:cli-range-list-syntax;
      key "id";
      leaf id {
        type uint16;
      }
      uses vlan-bd-config-grouping;
      leaf mode {
        type enumeration {
          enum "ce";
          enum "fabricpath";
        }
      }
      container fcoe {
        leaf vsan {
          type uint16;
        }
      }
      leaf name {
        type string;
      }
      leaf shutdown {
        type boolean;
      }
      leaf state {
        type enumeration {
          enum "active";
          enum "suspend";
        }
      }
      leaf vn-segment {
        type uint32;
      }
      container private-vlan {
        choice vlan-type {
          leaf community {
            type empty;
          }
          leaf isolated {
            type empty;
          }
          leaf primary {
            type empty;
          }
        }
        leaf-list association {
          tailf:cli-range-list-syntax;
          type uint16;
        }
      }
    }
    list configuration {
      tailf:cli-range-list-syntax;
      key "id";
      leaf id {
        type uint16;
      }
      uses vlan-bd-config-grouping;
    }
    list access-map {
      key "name";
      leaf name {
        tailf:cli-multi-word-key;
        type string;
      }
      container match {
        container ip {
          leaf address {
            type string;
          }
        }
        container ipv6 {
          leaf address {
            type string;
          }
        }
        container mac {
          leaf address {
            type string;
          }
        }
      }
      container action {
        choice action-choice {
          leaf drop {
            type empty;
          }
          leaf forward {
            type empty;
          }
          leaf redirect {
            type string;
          }
        }
      }
      container statistics {
        leaf per-entry {
          type empty;
        }
      }
    }
    list filter {
      tailf:cli-suppress-mode;
      tailf:cli-delete-when-empty;
      key "name";
      leaf name {
        type string;
      }
      leaf-list vlan-list {
        tailf:cli-range-list-syntax;
        type uint16;
      }
    }
    container dot1Q {
      container tag {
        leaf native {
          type empty;
        }
      }
    }
  }
  container evpn {
    tailf:cli-add-mode;
    presence "true";
    list evi {
      key "id";
      leaf id {
        type uint32;
      }
      leaf vni {
        tailf:cli-hide-in-submode;
        type empty;
      }
      container bgp {
        tailf:cli-add-mode;
        leaf rd {
          type string;
        }
        list route-target {
          tailf:cli-suppress-mode;
          tailf:cli-delete-when-empty;
          key "method";
          leaf method {
            type enumeration {
              enum "import";
              enum "export";
            }
          }
          leaf rt {
            tailf:cli-drop-node-name;
            type union {
              type enumeration {
                enum "auto";
              }
              type asn-ip-type;
            }
          }
        }
      }
    }
    list vni {
      key "id";
      leaf id {
        type uint32;
      }
      leaf l2 {
        tailf:cli-hide-in-submode;
        type empty;
      }
      leaf rd {
        type union {
          type enumeration {
            enum "auto";
          }
          type asn-ip-type;
        }
      }
      list route-target {
        tailf:cli-suppress-mode;
        tailf:cli-delete-when-empty;
        key "method rt";
        leaf method {
          type enumeration {
            enum "import";
            enum "export";
          }
        }
        leaf rt {
          type union {
            type enumeration {
              enum "auto";
            }
            type asn-ip-type;
          }
        }
      }
    }
  }
  container evpn-flat-syntax {
    tailf:cli-drop-node-name;
    container evpn {
      container multisite {
        tailf:cli-add-mode;
        presence "true";
        leaf border-gateway {
          tailf:cli-hide-in-submode;
          type uint64;
        }
        container delay-restore {
          leaf time {
            type uint16;
          }
        }
        container split-horizon {
          leaf per-site {
            type empty;
          }
        }
      }
      container esi {
        leaf multihoming {
          type empty;
        }
      }
      container storm-control {

        grouping level-grouping {
          leaf level {
            type uint8;
          }
        }
        container broadcast {
          uses level-grouping;
        }
        container multicast {
          uses level-grouping;
        }
        container unicast {
          uses level-grouping;
        }
      }
    }
  }
  list route-map {
    tailf:cli-compact-syntax;
    key "name sequence";
    leaf name {
      type string;
    }
    leaf sequence {
      type uint16;
    }
    leaf operation {
      tailf:cli-drop-node-name;
      tailf:cli-prefix-key {
        tailf:cli-before-key "2";
      }
      type enumeration {
        enum "deny";
        enum "permit";
      }
    }
    container match {
      container ip {
        uses addr-match-grouping;
        container multicast {
          choice type-choice {
            leaf group {
              type tailf:ipv4-address-and-prefix-length;
            }
            container group-range {
              tailf:cli-compact-syntax;
              tailf:cli-sequence-commands {
                tailf:cli-reset-siblings;
              }
              leaf first {
                tailf:cli-drop-node-name;
                type inet:ipv4-address;
              }
              leaf to {
                type inet:ipv4-address;
              }
            }
            leaf rp {
              type tailf:ipv4-address-and-prefix-length;
            }
            leaf source {
              type tailf:ipv4-address-and-prefix-length;
            }
          }
        }
        container next-hop {
          leaf-list prefix-list {
            tailf:cli-flat-list-syntax;
            ordered-by user;
            type string;
          }
        }
      }
      container ipv6 {
        uses addr-match-grouping;
      }
      leaf-list tag {
        tailf:cli-flat-list-syntax;
        type uint32;
      }
      container as-number {
        leaf-list as-path-list {
          tailf:cli-flat-list-syntax;
          ordered-by user;
          type string;
        }
        leaf-list as-number {
          tailf:cli-drop-node-name;
          tailf:cli-flat-list-syntax;
          type string;
        }
      }
      leaf-list as-path {
        tailf:cli-flat-list-syntax;
        type string;
      }
      leaf-list community {
        tailf:cli-flat-list-syntax;
        type string;
      }
      leaf-list extcommunity {
        tailf:cli-flat-list-syntax;
        type string;
      }
      leaf-list route-type {
        tailf:cli-flat-list-syntax;
        type enumeration {
          enum "external";
          enum "inter-area";
          enum "internal";
          enum "intra-area";
          enum "level-1";
          enum "level-2";
          enum "local";
          enum "nssa-external";
          enum "type-1";
          enum "type-2";
        }
      }
      container evpn {
        leaf-list route-type {
          tailf:cli-flat-list-syntax;
          type enumeration {
            enum "1";
            enum "2";
            enum "2-mac-ip";
            enum "2-mac-only";
            enum "3";
            enum "4";
            enum "5";
            enum "6";
          }
        }
      }
      leaf-list metric {
        tailf:cli-flat-list-syntax;
        type uint32;
      }
      leaf-list interface {
        tailf:cli-flat-list-syntax;
        type string;
      }
      leaf-list mac-list {
        tailf:cli-flat-list-syntax;
        type string;
      }
      leaf-list ospf-area {
        tailf:cli-flat-list-syntax;
        ordered-by user;
        type uint32;
      }
      leaf-list source-protocol {
        tailf:cli-flat-list-syntax;
        type string;
      }
    }
    container set {
      container as-path {
        container prepend {
          leaf as-list {
            tailf:cli-drop-node-name;
            tailf:cli-multi-value;
            type string;
          }
          leaf last-as {
            type uint8;
          }
        }
        leaf tag {
          type empty;
        }
      }
      leaf distance {
        type uint8;
      }
      leaf interface {
        type enumeration {
          enum "Null0";
        }
      }
      container ip {
        container next-hop {
          tailf:cli-compact-syntax;
          leaf-list next-hop-addr {
            tailf:cli-drop-node-name;
            tailf:cli-flat-list-syntax;
            ordered-by user;
            type inet:ipv4-address;
          }
          leaf load-share {
            type empty;
          }
          leaf peer-address {
            type empty;
          }
          leaf redist-unchanged {
            type empty;
          }
          leaf unchanged {
            type empty;
          }
          list verify-availability {
            tailf:cli-suppress-mode;
            tailf:cli-delete-when-empty;
            tailf:cli-compact-syntax;
            ordered-by user;
            key "addr";
            leaf addr {
              type inet:ipv4-address;
            }
            leaf track {
              type uint16;
            }
            leaf load-share {
              type empty;
            }
          }
        }
      }
      container ipv6 {
        container next-hop {
          tailf:cli-compact-syntax;
          leaf-list next-hop-addr {
            ordered-by user;
            tailf:cli-drop-node-name;
            tailf:cli-flat-list-syntax;
            type inet:ipv6-address;
          }
          leaf load-share {
            type empty;
          }
          leaf peer-address {
            type empty;
          }
          leaf redist-unchanged {
            type empty;
          }
          leaf unchanged {
            type empty;
          }
          list verify-availability {
            tailf:cli-suppress-mode;
            tailf:cli-delete-when-empty;
            tailf:cli-compact-syntax;
            ordered-by user;
            key "addr";
            leaf addr {
              type inet:ipv6-address;
            }
            leaf track {
              type uint16;
            }
            leaf load-share {
              type empty;
            }
          }
        }
      }
      leaf label-index {
        type uint32;
      }
      leaf local-preference {
        type uint32;
      }
      container metric {
        tailf:cli-compact-syntax;
        tailf:cli-sequence-commands {
          tailf:cli-reset-siblings;
        }
        leaf value {
          tailf:cli-drop-node-name;
          type string;
        }
        leaf igrp-delay {
          tailf:cli-drop-node-name;
          type uint32;
        }
        leaf igrp-reliability {
          tailf:cli-drop-node-name;
          type uint8;
        }
        leaf igrp-effective {
          tailf:cli-drop-node-name;
          type uint8;
        }
        leaf igrp-mtu {
          tailf:cli-drop-node-name;
          type uint32;
        }
      }
      leaf metric-type {
        type enumeration {
          enum "external";
          enum "internal";
          enum "type-1";
          enum "type-2";
        }
      }
      leaf nssa-only {
        type empty;
      }
      container community {
        tailf:cli-sequence-commands;
        tailf:cli-compact-syntax;
        choice number-or-none-choice {
          case number {
            leaf-list community-number {
              tailf:cli-drop-node-name;
              tailf:cli-flat-list-syntax;
              type union {
                type uint32;
                type enumeration {
                  enum "internet";
                  enum "local-AS";
                  enum "no-advertise";
                  enum "no-export";
                }
                type string;
              }
            }
            leaf additive {
              type empty;
            }
          }
          leaf none {
            type empty;
          }
        }
      }
      container extcommunity {
        container four-byteas-generic {
          tailf:alt-name "4byteas-generic";
          choice set-or-none-choice {
            leaf none {
              type empty;
            }
            container set {
              tailf:cli-drop-node-name;
              list transitive {
                tailf:cli-suppress-mode;
                tailf:cli-delete-when-empty;
                key "number";
                leaf number {
                  type string;
                }
              }
              list non-transitive {
                tailf:cli-suppress-mode;
                tailf:cli-delete-when-empty;
                key "number";
                leaf number {
                  type string;
                }
              }
              leaf additive {
                type empty;
              }
            }
          }
        }
        container cost {
          list pre-bestpath {
            tailf:cli-suppress-mode;
            tailf:cli-delete-when-empty;
            key "id";
            leaf id {
              type uint8;
            }
            leaf cost {
              tailf:cli-drop-node-name;
              type uint32;
            }
          }
          list igp {
            tailf:cli-suppress-mode;
            tailf:cli-delete-when-empty;
            key "id";
            leaf id {
              type uint8;
            }
            leaf cost {
              tailf:cli-drop-node-name;
              type uint32;
            }
          }
        }
        container rt {
          tailf:cli-sequence-commands {
            tailf:cli-reset-siblings;
          }
          tailf:cli-compact-syntax;
          leaf-list ext-comm {
            tailf:cli-drop-node-name;
            tailf:cli-flat-list-syntax;
            type asn-ip-type;
          }
          leaf additive {
            type empty;
          }
        }
      }
      leaf tag {
        type uint32;
      }
      container path-selection {
        container all {
          leaf advertise {
            type empty;
          }
        }
      }
      leaf vrf {
        type vrf-member-type;
      }
      leaf weight {
        type uint16;
      }
      leaf origin {
        type enumeration {
          enum "egp";
          enum "igp";
          enum "incomplete";
        }
      }
    }
    leaf description {
      tailf:cli-multi-value;
      type string;
    }
    leaf continue {
      type uint16;
    }
  }
  container pbr-stats-route-map {
    tailf:cli-drop-node-name;
    list route-map {
      tailf:cli-suppress-mode;
      tailf:cli-delete-when-empty;
      tailf:cli-compact-syntax;
      key "name";
      leaf name {
        type string;
      }
      leaf pbr-statistics {
        type empty;
      }
    }
  }

  grouping addr-match-grouping {
    container address {
      leaf-list prefix-list {
        tailf:cli-flat-list-syntax;
        ordered-by user;
        type string;
      }
      leaf access-list {
        tailf:cli-drop-node-name;
        type string;
      }
    }
  }

  container class-map {
    container type {
      list qos {
        key "name";
        leaf name {
          type class-name-type;
        }
        leaf prematch {
          tailf:cli-prefix-key;
          tailf:cli-drop-node-name;
          type enumeration {
            enum "match-all";
            enum "match-any";
          }
        }
        leaf description {
          tailf:cli-multi-value;
          type string;
        }
        container match {
          uses match-grouping;
        }
      }
      list network-qos {
        key "name";
        leaf name {
          type class-name-type;
        }
        leaf prematch {
          tailf:cli-prefix-key;
          tailf:cli-drop-node-name;
          type enumeration {
            enum "match-any";
          }
        }
        leaf description {
          tailf:cli-multi-value;
          type string;
        }
        container match {
          leaf qos-group {
            type uint8;
          }
        }
      }
      list queuing {
        key "name";
        leaf name {
          type class-name-type;
        }
        leaf prematch {
          tailf:cli-prefix-key;
          tailf:cli-drop-node-name;
          type enumeration {
            enum "match-any";
          }
        }
        leaf description {
          tailf:cli-multi-value;
          type string;
        }
        container match {
          leaf qos-group {
            type uint8;
          }
          uses match-grouping;
        }
      }
      list control-plane {
        key "name";
        leaf name {
          type class-name-type;
        }
        leaf prematch {
          tailf:cli-prefix-key;
          tailf:cli-drop-node-name;
          type enumeration {
            enum "match-all";
            enum "match-any";
          }
        }
        container match {
          container access-group {
            leaf-list name {
              type string;
            }
          }
          container protocol {
            leaf arp {
              type empty;
            }
            container mpls {
              tailf:cli-delete-when-empty;
              presence "true";
              leaf router-alert {
                type empty;
              }
              leaf exp {
                type uint8;
              }
            }
          }
          container redirect {
            leaf arp-inspect {
              type empty;
            }
            leaf dhcp-snoop {
              type empty;
            }
          }
          container exception {
            container ip {
              uses class-map-match-exception-ip-grouping;
            }
            container ipv6 {
              uses class-map-match-exception-ip-grouping;
            }
            container multicast {
              leaf dest-miss {
                type empty;
              }
              leaf ipv6-dest-miss {
                type empty;
              }
              leaf ipv6-rpf-failure {
                type empty;
              }
              leaf ipv6-sg-rpf-failure {
                type empty;
              }
              leaf rpf-failure {
                type empty;
              }
              leaf sg-rpf-failure {
                type empty;
              }
              leaf directly-connected-sources {
                type empty;
              }
            }
            leaf fcoe-fib-miss {
              type empty;
            }
            leaf glean {
              type empty;
            }
            leaf mtu-failure {
              type empty;
            }
            leaf mvpn {
              type empty;
            }
            leaf nat-flow {
              type empty;
            }
            leaf ttl-failure {
              type empty;
            }
            leaf sflow {
              type empty;
            }
          }
        }
      }
    }
  }

  grouping match-grouping {
    container access-group {
      leaf-list name {
        type string;
      }
    }
    leaf-list cos {
      tailf:cli-range-list-syntax;
      type uint16;
    }
    leaf-list dscp {
      tailf:cli-range-list-syntax;
      type dscp-type;
    }
    container ip {
      leaf-list rtp {
        tailf:cli-range-list-syntax;
        type uint16;
      }
    }
    leaf-list precedence {
      tailf:cli-range-list-syntax;
      type uint8;
    }
    container protocol {
      leaf arp {
        type empty;
      }
      leaf clns_es {
        type empty;
      }
      leaf clns_is {
        type empty;
      }
      leaf dhcp {
        type empty;
      }
      leaf ldp {
        type empty;
      }
      leaf netbios {
        type empty;
      }
    }
    container packet {
      leaf-list length {
        tailf:cli-range-list-syntax;
        type uint16;
      }
    }
  }

  container control-plane {
    tailf:cli-add-mode;
    container scale-factor {
      tailf:cli-compact-syntax;
      tailf:cli-sequence-commands {
        tailf:cli-reset-siblings;
      }
      leaf scale {
        tailf:cli-drop-node-name;
        type decimal64 {
          fraction-digits 2;
        }
      }
      leaf module {
        type uint8;
      }
    }
    container service-policy {
      leaf input {
        type string;
      }
    }
  }
  container ntp {
    leaf authenticate {
      type empty;
    }
    list authentication-key {
      tailf:cli-suppress-mode;
      tailf:cli-delete-when-empty;
      tailf:cli-compact-syntax;
      tailf:cli-sequence-commands;
      key "id";
      leaf id {
        type uint16;
      }
      leaf md5 {
        type string;
      }
      leaf encryption-type {
        tailf:cli-drop-node-name;
        type enumeration {
          enum "0";
          enum "7";
        }
      }
    }
    leaf trusted-key {
      type uint16;
    }
    leaf commit {
      type empty;
    }
    leaf distribute {
      type empty;
    }
    list peer {
      tailf:cli-suppress-mode;
      tailf:cli-delete-when-empty;
      tailf:cli-compact-syntax;
      tailf:cli-sequence-commands {
        tailf:cli-reset-all-siblings;
      }
      key "id";
      leaf id {
        type inet:ipv4-address;
      }
      leaf prefer {
        tailf:cli-optional-in-sequence;
        type empty;
      }
      leaf use-vrf {
        type string;
      }
      leaf key {
        tailf:cli-optional-in-sequence;
        type uint16;
      }
      leaf minpoll {
        type uint8;
      }
      leaf maxpoll {
        type uint8;
      }
    }
    list server {
      tailf:cli-suppress-mode;
      tailf:cli-delete-when-empty;
      tailf:cli-compact-syntax;
      key "id";
      leaf id {
        type string;
      }
      leaf prefer {
        type empty;
      }
      leaf use-vrf {
        type vrf-member-type;
      }
      leaf key {
        type uint16;
      }
    }
    leaf source-interface {
      type string;
    }
    container source {
      leaf ipv6-address {
        tailf:cli-drop-node-name;
        type inet:ipv6-address;
      }
      leaf ipv4-address {
        tailf:cli-drop-node-name;
        type inet:ip-address;
      }
    }
    container access-group {
      list peer {
        tailf:cli-suppress-mode;
        key "name";
        leaf name {
          type string;
        }
      }
      list serve {
        tailf:cli-suppress-mode;
        key "name";
        leaf name {
          type string;
        }
      }
      list query-only {
        tailf:cli-suppress-mode;
        key "name";
        leaf name {
          type string;
        }
      }
      list serve-only {
        tailf:cli-suppress-mode;
        key "name";
        leaf name {
          type string;
        }
      }
      leaf match-all {
        type empty;
      }
    }
    leaf logging {
      type empty;
    }
    leaf master {
      type uint8;
    }
  }
  container service {
    leaf dhcp {
      type empty;
    }
    leaf unsupported-transceiver {
      type boolean;
    }
  }
  container key {
    list chain {
      key "name";
      leaf name {
        type string;
      }
      leaf type {
        tailf:cli-drop-node-name;
        tailf:cli-hide-in-submode;
        type enumeration {
          enum "macsec";
          enum "tunnel-encryption";
        }
      }
      list key {
        key "id";
        leaf id {
          type union {
            type uint16;
            type string;
          }
        }
        leaf cryptographic-algorithm {
          type enumeration {
            enum "MD5";
            enum "HMAC-SHA-1";
            enum "HMAC-SHA-256";
            enum "HMAC-SHA-384";
            enum "HMAC-SHA-512";
          }
        }
        container key-string {
          tailf:cli-compact-syntax;
          tailf:cli-sequence-commands;
          leaf key-type {
            tailf:cli-drop-node-name;
            type enumeration {
              enum "0";
              enum "7";
            }
          }
          leaf key-value {
            tailf:cli-drop-node-name;
            type string;
          }
        }
        container key-octet-string {
          tailf:cli-compact-syntax;
          tailf:cli-sequence-commands;
          leaf key-type {
            tailf:cli-drop-node-name;
            type enumeration {
              enum "0";
              enum "6";
              enum "7";
            }
          }
          leaf key-value {
            tailf:cli-drop-node-name;
            type string;
          }
          leaf cryptographic-algorithm {
            type enumeration {
              enum "AES_128_CMAC";
              enum "AES_256_CMAC";
            }
          }
        }
        container accept-lifetime {
          tailf:cli-compact-syntax;
          tailf:cli-sequence-commands {
            tailf:cli-reset-siblings;
          }
          uses lifetime-grouping;
        }
        container send-lifetime {
          tailf:cli-compact-syntax;
          tailf:cli-sequence-commands {
            tailf:cli-reset-siblings;
          }
          uses lifetime-grouping;
        }
      }
    }
  }
  container key-chain {
    container macsec-psk {
      leaf no-show {
        type empty;
      }
    }
    container tunnelencrypt-psk {
      leaf no-show {
        type empty;
      }
    }
  }
  container flow {
    list event {
      key "name";
      leaf name {
        type string;
      }
      leaf description {
        tailf:cli-multi-value;
        type string;
      }
      container group {
        container drop-events {
          tailf:cli-add-mode;
          container capture {
            leaf acl-drops {
              type empty;
            }
            leaf buffer-drops {
              type empty;
            }
            leaf fwd-drops {
              type empty;
            }
          }
        }
        container latency-events {
          tailf:cli-add-mode;
          container capture {
            container latency {
              tailf:cli-compact-syntax;
              tailf:cli-sequence-commands {
                tailf:cli-reset-all-siblings;
              }
              leaf exceeding-threshold {
                type uint16;
              }
              leaf unit {
                tailf:cli-drop-node-name;
                type enumeration {
                  enum "micro-sec";
                  enum "milli-sec";
                }
              }
            }
          }
        }
        container packet-events {
          tailf:cli-add-mode;
          container capture {
            leaf ip-df {
              type empty;
            }
            leaf rcv-window-zero {
              type empty;
            }
            leaf tos {
              type uint8;
            }
            leaf ttl {
              type uint8;
            }
          }
        }
      }
    }
    list exporter {
      key "name";
      leaf name {
        type string;
      }
      leaf description {
        tailf:cli-multi-value;
        type string;
      }
      container destination {
        tailf:cli-sequence-commands {
          tailf:cli-reset-all-siblings;
        }
        tailf:cli-compact-syntax;
        leaf address {
          tailf:cli-drop-node-name;
          type union {
            type inet:ip-address;
            type inet:ipv6-address;
          }
        }
        leaf use-vrf {
          type vrf-member-type;
        }
      }
      container transport {
        leaf udp {
          type uint16;
        }
      }
      leaf source {
        type string;
      }
      container version {
        tailf:cli-add-mode;
        leaf version {
          tailf:cli-drop-node-name;
          tailf:cli-hide-in-submode;
          type enumeration {
            enum "5";
            enum "9";
          }
        }
        container option {

          grouping timeout-grp {
            leaf timeout {
              type uint32;
            }
          }
          container arp-table {
            uses timeout-grp;
          }
          container exporter-stats {
            uses timeout-grp;
          }
          container interface-stats {
            uses timeout-grp;
          }
          container interface-table {
            uses timeout-grp;
          }
          container sampler-table {
            uses timeout-grp;
          }
        }
        container template {
          container data {
            leaf timeout {
              type uint32;
            }
          }
        }
      }
      leaf dscp {
        type uint8;
      }
    }
    list filter {
      key "name";
      leaf name {
        type string;
      }
      leaf ipv4 {
        type string;
      }
      leaf ipv6 {
        type string;
      }
    }
    list monitor {
      key "name";
      leaf name {
        type string;
      }
      leaf description {
        tailf:cli-multi-value;
        type string;
      }
      list exporter-bucket-id {
        key "id";
        leaf id {
          type uint8;
        }
        leaf low {
          tailf:cli-drop-node-name;
          tailf:cli-hide-in-submode;
          mandatory true;
          type uint16;
        }
        leaf high {
          tailf:cli-drop-node-name;
          tailf:cli-hide-in-submode;
          mandatory true;
          type uint16;
        }
        list exporter {
          tailf:cli-suppress-mode;
          tailf:cli-delete-when-empty;
          key "name";
          leaf name {
            type string;
          }
        }
      }
      container record {
        choice record-choice {
          container netflow {
            choice collection-choice {
              leaf ipv4 {
                type enumeration {
                  enum "original-input";
                  enum "original-output";
                }
              }
              leaf ipv6 {
                type enumeration {
                  enum "original-input";
                  enum "original-output";
                }
              }
              container layer2-switched {
                leaf input {
                  type empty;
                }
              }
              leaf protocol-port {
                type empty;
              }
            }
          }
          leaf netflow-original {
            type empty;
          }
          leaf record-name {
            tailf:cli-drop-node-name;
            type string;
          }
        }
      }
      list exporter {
        tailf:cli-suppress-mode;
        tailf:cli-delete-when-empty;
        key "name";
        leaf name {
          type string;
        }
      }
    }
    list profile {
      key "name";
      leaf name {
        type string;
      }
      container collect {
        leaf interval {
          type uint16;
        }
      }
      container source {
        leaf port {
          type uint16;
        }
      }
    }
    list record {
      key "name";
      leaf name {
        type string;
      }
      container collect {
        container counter {
          choice counter-bytes-choice {
            leaf bytes {
              type empty;
            }
            container bytes-long {
              tailf:cli-drop-node-name;
              container bytes {
                leaf long {
                  type empty;
                }
              }
            }
          }
          choice counter-packets-choice {
            leaf packets {
              type empty;
            }
            container packets-long {
              tailf:cli-drop-node-name;
              container packets {
                leaf long {
                  type empty;
                }
              }
            }
          }
        }
        container flow {
          container sampler {
            leaf id {
              type empty;
            }
          }
        }
        container ip {
          leaf version {
            type empty;
          }
        }
        container routing {
          container destination {
            leaf as {
              type empty;
            }
            container as-peer {
              tailf:cli-drop-node-name;
              container as {
                leaf peer {
                  type empty;
                }
              }
            }
          }
          leaf forwarding-status {
            type empty;
          }
          container next-hop {
            container address {
              leaf ipv4 {
                type empty;
              }
              container ipv4-bgp {
                tailf:cli-drop-node-name;
                container ipv4 {
                  leaf bgp {
                    type empty;
                  }
                }
              }
              leaf ipv6 {
                type empty;
              }
              container ipv6-bgp {
                tailf:cli-drop-node-name;
                container ipv6 {
                  leaf bgp {
                    type empty;
                  }
                }
              }
            }
          }
          container source {
            leaf as {
              type empty;
            }
            container as-peer {
              tailf:cli-drop-node-name;
              container as {
                leaf peer {
                  type empty;
                }
              }
            }
          }
        }
        container timestamp {
          container sys-uptime {
            leaf first {
              type empty;
            }
            leaf last {
              type empty;
            }
          }
        }
        container transport {
          container tcp {
            leaf flags {
              type empty;
            }
          }
        }
      }
      leaf description {
        tailf:cli-multi-value;
        type string;
      }
      container match {
        container datalink {
          leaf ethertype {
            type empty;
          }
          container mac {
            leaf destination-address {
              type empty;
            }
            leaf source-address {
              type empty;
            }
          }
          leaf vlan {
            type empty;
          }
        }
        container ip {
          leaf protocol {
            type empty;
          }
          leaf tos {
            type empty;
          }
          container destination {
            leaf address {
              type empty;
            }
          }
          container source {
            leaf address {
              type empty;
            }
          }
        }
        container ipv4 {
          container destination {
            leaf address {
              type empty;
            }
          }
          container source {
            leaf address {
              type empty;
            }
          }
        }
        container ipv6 {
          container destination {
            leaf address {
              type empty;
            }
          }
          leaf flow-label {
            type empty;
          }
          leaf options {
            type empty;
          }
          container source {
            leaf address {
              type empty;
            }
          }
        }
        container transport {
          leaf destination-port {
            type empty;
          }
          leaf source-port {
            type empty;
          }
        }
      }
    }
    container system {
      container config {
        tailf:cli-add-mode;
        leaf exporter-id {
          type uint16;
        }
        container monitor {
          tailf:cli-compact-syntax;
          tailf:cli-sequence-commands {
            tailf:cli-reset-all-siblings;
          }
          leaf name {
            tailf:cli-drop-node-name;
            type string;
          }
          leaf input {
            type empty;
          }
        }
        leaf profile {
          type string;
        }
        leaf event {
          type string;
        }
        leaf filter {
          type string;
        }
      }
    }
    container timeout {
      leaf f2-timeout {
        tailf:cli-drop-node-name;
        type uint8;
      }
      leaf active {
        type uint16;
      }
      leaf inactive {
        type uint16;
      }
      container aggressive {
        leaf threshold {
          type uint8;
        }
      }
      container fast {
        tailf:cli-sequence-commands {
          tailf:cli-reset-siblings;
        }
        tailf:cli-compact-syntax;
        leaf time {
          tailf:cli-drop-node-name;
          type uint16;
        }
        leaf threshold {
          type uint16;
        }
      }
      leaf session {
        type empty;
      }
    }
  }
  list sampler {
    key "name";
    leaf name {
      type string;
    }
    container mode {
      tailf:cli-sequence-commands {
        tailf:cli-reset-all-siblings;
      }
      tailf:cli-compact-syntax;
      leaf num-samples {
        tailf:cli-drop-node-name;
        type uint8;
      }
      leaf out-of {
        type uint32;
      }
    }
  }
  container udld {
    leaf aggressive {
      type empty;
    }
    leaf message-time {
      type uint8;
    }
  }
  container vrf {
    list context {
      key "id";
      leaf id {
        type vrf-member-type;
      }
      leaf description {
        tailf:cli-multi-value;
        type string;
      }
      container vni {
        tailf:cli-compact-syntax;
        tailf:cli-sequence-commands {
          tailf:cli-reset-siblings;
        }
        leaf id {
          tailf:cli-drop-node-name;
          type uint32;
        }
        leaf l3 {
          type empty;
        }
      }
      leaf rd {
        type union {
          type enumeration {
            enum "auto";
          }
          type asn-ip-type;
        }
      }
      container address-family {

        grouping unicast-grouping {
          container unicast {
            tailf:cli-add-mode;
            presence "true";
            list route-target {
              tailf:cli-suppress-mode;
              tailf:cli-delete-when-empty;
              key "method asn target-evpn";
              leaf method {
                type enumeration {
                  enum "both";
                  enum "export";
                  enum "import";
                }
              }
              leaf asn {
                type union {
                  type enumeration {
                    enum "auto";
                  }
                  type asn-ip-type;
                  type string;
                }
              }
              leaf target-evpn {
                type enumeration {
                  enum "evpn";
                  enum "non-evpn";
                  enum "mvpn";
                }
              }
            }
            container export {
              leaf map {
                type string;
              }
            }
            container export-vrf {
              tailf:cli-drop-node-name;
              container export {
                tailf:cli-compact-syntax;
                tailf:cli-sequence-commands {
                  tailf:cli-reset-siblings;
                }
                leaf vrf {
                  type vrf-member-type;
                }
                leaf max-limit {
                  tailf:cli-drop-node-name;
                  tailf:cli-optional-in-sequence;
                  type uint32;
                }
                leaf map {
                  type string;
                }
                leaf allow-vpn {
                  type empty;
                }
              }
            }
            container import {
              leaf map {
                type string;
              }
            }
            container import-vrf {
              tailf:cli-drop-node-name;
              container import {
                tailf:cli-compact-syntax;
                tailf:cli-sequence-commands {
                  tailf:cli-reset-siblings;
                }
                leaf vrf {
                  type vrf-member-type;
                }
                leaf max-limit {
                  tailf:cli-drop-node-name;
                  tailf:cli-optional-in-sequence;
                  type uint32;
                }
                leaf map {
                  type string;
                }
                leaf advertise-vpn {
                  type empty;
                }
              }
            }
            container maximum {
              tailf:cli-compact-syntax;
              tailf:cli-sequence-commands {
                tailf:cli-reset-all-siblings;
              }
              leaf routes {
                type uint32;
              }
              choice warn-or-threshold-choice {
                case threshold {
                  leaf threshold {
                    tailf:cli-drop-node-name;
                    type uint8;
                  }
                  leaf reinstall {
                    type uint8;
                  }
                }
                case warning {
                  leaf warning-only {
                    type empty;
                  }
                }
              }
            }
          }
        }
        container ipv4 {
          uses unicast-grouping;
        }
        container ipv6 {
          uses unicast-grouping;
        }
      }
      container ip {
        uses ip-grouping;
        leaf auto-discard {
          type empty;
        }
      }
      container ipv6 {
        uses ipv6-grouping;
      }
      container cts {
        container role-based {
          list sgt-map {
            tailf:cli-suppress-mode;
            tailf:cli-delete-when-empty;
            key "addr";
            leaf addr {
              type union {
                type inet:ipv4-address;
                type tailf:ipv4-address-and-prefix-length;
              }
            }
            leaf sgt {
              tailf:cli-drop-node-name;
              type uint16;
            }
          }
        }
      }
    }
  }
  container ptp {
    container correction-range {
      leaf threshold {
        tailf:cli-drop-node-name;
        type uint32;
      }
      leaf logging {
        type empty;
      }
    }
    leaf domain {
      type uint8;
    }
    leaf management {
      type boolean;
    }
    leaf mean-path-delay {
      type uint32;
    }
    container notification {
      container type {
        tailf:cli-sequence-commands {
          tailf:cli-reset-siblings;
        }
        tailf:cli-compact-syntax;
        leaf high-correction {
          type empty;
        }
        leaf interval {
          type union {
            type uint16;
            type enumeration {
              enum "immediate";
            }
          }
        }
        leaf periodic-notification {
          type enumeration {
            enum "disable";
            enum "enable";
          }
        }
      }
    }
    leaf priority1 {
      type uint8;
    }
    leaf priority2 {
      type uint8;
    }
    container source {
      tailf:cli-sequence-commands {
        tailf:cli-reset-siblings;
      }
      tailf:cli-compact-syntax;
      leaf address {
        tailf:cli-drop-node-name;
        type inet:ipv4-address;
      }
      leaf vrf {
        type string;
      }
    }
    container profile {
      tailf:cli-add-mode;
      presence "true";
      leaf type {
        tailf:cli-drop-node-name;
        tailf:cli-hide-in-submode;
        type enumeration {
          enum "8275-1";
          enum "default";
        }
      }
    }
  }
  container hsrp {
    list anycast {
      key "bundle proto";
      leaf bundle {
        type uint16;
      }
      leaf proto {
        type enumeration {
          enum "both";
          enum "ipv4";
          enum "ipv6";
        }
      }
      leaf priority {
        type uint8;
      }
      leaf switch-id {
        type uint16;
      }
      leaf-list vlan {
        tailf:cli-range-list-syntax;
        type uint16;
      }
      leaf shutdown {
        type boolean;
      }
    }
    container bfd {
      leaf all-interfaces {
        type empty;
      }
    }
    container timers {
      container extended-hold {
        presence "true";
        leaf value {
          tailf:cli-drop-node-name;
          type uint8;
        }
      }
    }
  }
  container sflow {
    leaf agent-ip {
      type inet:ipv4-address;
    }
    container collector-ip {
      tailf:cli-compact-syntax;
      tailf:cli-sequence-commands {
        tailf:cli-reset-siblings;
      }
      leaf address {
        tailf:cli-drop-node-name;
        type inet:ipv4-address;
      }
      leaf vrf {
        type vrf-member-type;
      }
      leaf source {
        type inet:ipv4-address;
      }
    }
    leaf collector-port {
      type uint16;
    }
    leaf counter-poll-interval {
      type uint32;
    }
    container data-source {
      list interface {
        tailf:cli-suppress-mode;
        key "name";
        leaf name {
          type string;
        }
      }
    }
    container extended {
      leaf switch {
        type empty;
      }
    }
    leaf max-datagram-size {
      type uint16;
    }
    leaf max-sampled-size {
      type uint16;
    }
    leaf sampling-rate {
      type uint32;
    }
  }
  container vpc {
    container domain {
      tailf:cli-add-mode;
      presence "true";
      leaf id {
        tailf:cli-drop-node-name;
        tailf:cli-hide-in-submode;
        mandatory true;
        type uint16;
      }
      choice enable-or-disable-auto-recovery {
        case auto-recovery {
          container auto-recovery {
            leaf reload-delay {
              type uint16;
            }
          }
        }
        container disable {
          tailf:cli-drop-node-name;
          leaf auto-recovery {
            type boolean;
          }
        }
      }
      container delay {
        leaf restore {
          type uint16;
        }
        container other-delay {
          tailf:cli-drop-node-name;
          container restore {
            leaf interface-vlan {
              type uint16;
            }
            leaf orphan-port {
              type uint16;
            }
          }
        }
      }
      container ipv6 {
        container nd {
          leaf synchronize {
            type empty;
          }
        }
      }
      container ip {
        leaf arp {
          type enumeration {
            enum "synchronize";
          }
        }
      }
      leaf peer-gateway {
        type empty;
      }
      container peer-keepalive {
        tailf:cli-compact-syntax;
        tailf:cli-sequence-commands {
          tailf:cli-reset-siblings;
        }
        leaf destination {
          type inet:ipv4-address;
        }
        leaf source {
          type inet:ipv4-address;
        }
        leaf udp-port {
          tailf:cli-break-sequence-commands;
          type uint16;
        }
        leaf vrf {
          type string;
        }
        leaf interval {
          type uint16;
        }
        leaf timeout {
          type uint8;
        }
        leaf precedence {
          type uint8;
        }
        leaf hold-timeout {
          type uint8;
        }
      }
      container virtual {
        container peer-link {
          tailf:cli-compact-syntax;
          tailf:cli-sequence-commands {
            tailf:cli-reset-siblings;
          }
          leaf destination {
            type inet:ipv4-address;
          }
          leaf source {
            type union {
              type inet:ipv4-address;
              type tailf:ipv4-address-and-prefix-length;
            }
          }
          leaf dscp {
            type dscp-type;
          }
        }
      }
      leaf peer-switch {
        type empty;
      }
      container role {
        leaf priority {
          type string;
        }
      }
      container fabricpath {
        leaf switch-id {
          type uint16;
        }
        container multicast {
          leaf load-balance {
            type boolean;
          }
        }
      }
      leaf system-priority {
        type uint16;
      }
      container layer3 {
        tailf:cli-case-insensitive;
        leaf peer-router {
          type empty;
        }
        container syslog-config {
          tailf:cli-drop-node-name;
          container peer-router {
            container syslog {
              choice enable-disable {
                case interval {
                  leaf interval {
                    type uint16;
                  }
                }
                leaf disable {
                  type empty;
                }
              }
            }
          }
        }
      }
      leaf track {
        type uint16;
      }
      container dual-active {
        container exclude {
          leaf-list interface-vlan {
            tailf:cli-range-list-syntax;
            type uint16;
          }
        }
      }
      leaf fast-convergence {
        type empty;
      }
      container graceful {
        leaf consistency-check {
          type empty;
        }
      }
      leaf shutdown {
        type empty;
      }
      leaf peer-config-check-bypass {
        type empty;
      }
      container bypass {
        leaf module-check {
          type empty;
        }
      }
    }
  }
  container lacp {
    leaf offload {
      type empty;
    }
    leaf system-priority {
      type uint16;
    }
  }
  container lldp {
    leaf reinit {
      type uint8;
    }
    leaf timer {
      type uint8;
    }
    leaf holdtime {
      type uint16;
    }
    leaf portid-subtype {
      type uint8;
    }
    container tlv-select {
      leaf dcbxp {
        type boolean;
      }
      container management-address {
        leaf v4 {
          type boolean;
        }
        leaf v6 {
          type boolean;
        }
      }
      leaf port-description {
        type boolean;
      }
      leaf port-vlan {
        type boolean;
      }
      leaf power-management {
        type boolean;
      }
      leaf four-wire-power-management {
        type boolean;
      }
      leaf system-capabilities {
        type boolean;
      }
      leaf system-description {
        type boolean;
      }
      leaf system-name {
        type boolean;
      }
    }
  }
  container port-channel {
    leaf hash-distribution {
      type enumeration {
        enum "adaptive";
        enum "fixed";
      }
    }
    container load-balance {
      leaf ethernet {
        type enumeration {
          enum "source-mac";
          enum "destination-ip";
          enum "destination-mac";
          enum "destination-port";
          enum "source-dest-ip";
          enum "source-dest-mac";
          enum "source-dest-port";
          enum "source-ip";
          enum "source-port";
          enum "source-dest-port-only";
          enum "source-dest-ip-only";
          enum "source-dest-ip-gre";
          enum "source-ip-gre";
          enum "destination-ip-gre";
        }
      }
      container load-balance-parameters {
        tailf:cli-drop-node-name;
        container global-parameters {
          tailf:cli-drop-node-name;
          tailf:cli-compact-syntax;
          tailf:cli-sequence-commands {
            tailf:cli-reset-all-siblings;
          }
          uses lb-parameters-grouping;
        }
        list module {
          tailf:cli-suppress-mode;
          tailf:cli-delete-when-empty;
          tailf:cli-compact-syntax;
          tailf:cli-sequence-commands {
            tailf:cli-reset-all-siblings;
          }
          key "id";
          leaf id {
            type uint8;
          }
          uses lb-parameters-grouping;
        }
        leaf hash-modulo {
          type empty;
        }
        leaf hash-modulo-f2 {
          type empty;
        }
      }
    }
  }

  grouping lb-parameters-grouping {
    leaf param-type {
      tailf:cli-drop-node-name;
      type enumeration {
        enum "dst";
        enum "src";
        enum "src-dst";
      }
    }
    leaf param-value {
      tailf:cli-drop-node-name;
      type enumeration {
        enum "ip";
        enum "ip-l4port";
        enum "ip-l4port-vlan";
        enum "ip-vlan";
        enum "l4port";
        enum "mac";
      }
    }
    leaf mpls {
      tailf:cli-optional-in-sequence;
      type enumeration {
        enum "label-ip";
        enum "label-only";
      }
    }
    leaf rotate {
      tailf:cli-optional-in-sequence;
      type uint8;
    }
    leaf asymmetric {
      type empty;
    }
  }

  container hardware {
    container access-list {
      container lou {
        container resource {
          leaf threshold {
            type uint8;
          }
        }
      }
      container update {
        leaf atomic {
          type boolean;
        }
        container default-result {
          leaf permit {
            type empty;
          }
        }
      }
      container tcam {
        uses tcam-region-grouping;
      }
      container resource {
        container feature {
          leaf bank-mapping {
            type empty;
          }
        }
      }
    }
    container forwarding {
      container unicast {
        leaf trace {
          type empty;
        }
      }
      container interface {
        container statistics {
          leaf mode {
            type enumeration {
              enum "default";
              enum "mpls";
              enum "invalid";
            }
          }
          container stats-per-module {
            tailf:cli-drop-node-name;
            list mode {
              tailf:cli-suppress-mode;
              tailf:cli-delete-when-empty;
              key "module";
              leaf module {
                tailf:cli-expose-key-name;
                type uint8;
              }
              leaf mode {
                tailf:cli-drop-node-name;
                tailf:cli-prefix-key;
                mandatory true;
                type enumeration {
                  enum "default";
                  enum "mpls";
                  enum "invalid";
                }
              }
            }
          }
        }
      }
    }
    container ip {
      container glean {
        container throttle {
          presence "true";
          leaf maximum {
            type uint16;
          }
          leaf syslog {
            type uint16;
          }
          leaf timeout {
            type uint16;
          }
        }
      }
      container verify {
        container address {
          container destination {
            leaf zero {
              type boolean;
            }
          }
          leaf identical {
            type boolean;
          }
          leaf reserved {
            type boolean;
          }
          container source {
            leaf broadcast {
              type boolean;
            }
            leaf multicast {
              type boolean;
            }
          }
        }
        leaf checksum {
          type boolean;
        }
        leaf fragment {
          type boolean;
        }
        container length {
          leaf consistent {
            type boolean;
          }
          container maximum {
            leaf max-frag {
              type boolean;
            }
            leaf max-tcp {
              type boolean;
            }
          }
          leaf minimum {
            type boolean;
          }
        }
        leaf protocol {
          type boolean;
        }
        leaf syslog {
          type boolean;
        }
        container tcp {
          leaf flags {
            type boolean;
          }
          leaf tiny-frag {
            type boolean;
          }
        }
        leaf version {
          type boolean;
        }
      }
    }
    container ipv6 {
      container glean {
        container throttle {
          presence "true";
          leaf maximum {
            type uint16;
          }
        }
      }
    }
    container rate-limiter {
      container layer-2 {
        leaf vpc-peer-gw {
          type union {
            type uint16;
            type enumeration {
              enum "disable";
            }
          }
        }
        container vpc-pgw-per-module {
          tailf:cli-drop-node-name;
          list vpc-peer-gw {
            tailf:cli-suppress-mode;
            tailf:cli-delete-when-empty;
            key "module";
            leaf module {
              tailf:cli-expose-key-name;
              type uint8;
            }
            leaf value {
              tailf:cli-drop-node-name;
              tailf:cli-prefix-key;
              mandatory true;
              type union {
                type uint16;
                type enumeration {
                  enum "disable";
                }
              }
            }
          }
        }
      }
      container layer-3 {
        leaf glean {
          type uint16;
        }
        container multicast {
          leaf local-groups {
            type union {
              type uint16;
              type enumeration {
                enum "disable";
              }
            }
          }
          container local-groups-per-module {
            tailf:cli-drop-node-name;
            list local-groups {
              tailf:cli-suppress-mode;
              tailf:cli-delete-when-empty;
              key "module";
              leaf module {
                tailf:cli-expose-key-name;
                type uint8;
              }
              leaf value {
                tailf:cli-drop-node-name;
                tailf:cli-prefix-key;
                mandatory true;
                type union {
                  type uint16;
                  type enumeration {
                    enum "disable";
                  }
                }
              }
            }
          }
          leaf directly-connected {
            type union {
              type uint16;
              type enumeration {
                enum "disable";
              }
            }
          }
          container directly-connected-per-module {
            tailf:cli-drop-node-name;
            list directly-connected {
              tailf:cli-suppress-mode;
              tailf:cli-delete-when-empty;
              key "module";
              leaf module {
                tailf:cli-expose-key-name;
                type uint8;
              }
              leaf value {
                tailf:cli-drop-node-name;
                tailf:cli-prefix-key;
                mandatory true;
                type union {
                  type uint16;
                  type enumeration {
                    enum "disable";
                  }
                }
              }
            }
          }
        }
      }
      container access-list-log {
        leaf packets {
          type uint32;
        }
        leaf packets-per-sec {
          tailf:cli-drop-node-name;
          type uint16;
        }
      }
      leaf span {
        type uint16;
      }
      container span-per-module {
        tailf:cli-drop-node-name;
        list span {
          tailf:cli-suppress-mode;
          tailf:cli-delete-when-empty;
          key "module";
          leaf module {
            tailf:cli-expose-key-name;
            type uint8;
          }
          leaf value {
            tailf:cli-drop-node-name;
            tailf:cli-prefix-key;
            mandatory true;
            type uint16;
          }
        }
      }
      leaf bfd {
        type uint32;
      }
      container bfd-per-module {
        tailf:cli-drop-node-name;
        list bfd {
          tailf:cli-suppress-mode;
          tailf:cli-delete-when-empty;
          key "module";
          leaf module {
            tailf:cli-expose-key-name;
            type uint8;
          }
          leaf value {
            tailf:cli-drop-node-name;
            tailf:cli-prefix-key;
            mandatory true;
            type uint32;
          }
        }
      }
    }
    container qos {
      leaf ns-buffer-profile {
        type enumeration {
          enum "burst";
          enum "mesh";
          enum "ultra-burst";
        }
      }
      container shared-buffer {
        list module {
          tailf:cli-suppress-mode;
          key "id";
          leaf id {
            type uint8;
          }
        }
      }
    }
    container profile {
      container tcam {
        container feature {
          container interface-qos {
            leaf limit {
              type tcam-size-type;
            }
          }
        }
        uses tcam-region-grouping;
      }
      leaf portmode {
        type string;
      }
      container multicast {
        leaf max-limit {
          type uint16;
        }
        container max-limit-lpm {
          tailf:cli-drop-node-name;
          container max-limit {
            leaf lpm-entries {
              type uint16;
            }
          }
        }
      }
      container buffer {
        container monitor {
          container sampling {
            leaf fast {
              type empty;
            }
          }
        }
      }
    }
    list module {
      key "id port-group";
      leaf id {
        type uint8;
      }
      leaf port-group {
        tailf:cli-expose-key-name;
        type uint8;
      }
      container qos {
        container shared-buffer {
          container queue-limit {
            leaf percent {
              type uint8;
            }
          }
        }
      }
    }
    container multicast {
      leaf disable-slow-port-pruning {
        type empty;
      }
      container snooping {
        leaf group-limit {
          type uint16;
        }
      }
    }
    container ejector {
      leaf enable {
        type boolean;
      }
    }
    container fabricpath {
      container mac-learning {
        list module {
          tailf:cli-suppress-mode;
          tailf:cli-delete-when-empty;
          key "id";
          leaf id {
            type uint8;
          }
          leaf port-group {
            type string;
          }
        }
      }
    }
  }
  container port-profile {
    container default {
      leaf max-ports {
        type uint16;
      }
      leaf port-binding {
        type enumeration {
          enum "static";
          enum "dynamic";
          enum "ephemeral";
        }
      }
    }
    list profiles {
      tailf:cli-drop-node-name;
      key "id";
      leaf id {
        type string;
      }
      leaf type {
        tailf:cli-prefix-key;
        type enumeration {
          enum "ethernet";
          enum "interface-vlan";
          enum "port-channel";
          enum "vethernet";
          enum "pseudowire";
          enum "tunnel-te";
        }
      }
      leaf max-ports {
        type uint16;
      }
      container capability {
        leaf l3control {
          type empty;
        }
        leaf vxlan {
          type empty;
        }
      }
      container vmware {
        leaf port-group {
          type empty;
        }
      }
      leaf shutdown {
        type empty;
      }
      leaf guid {
        type string;
      }
      leaf description {
        tailf:cli-multi-value;
        type string;
      }
      leaf state {
        type enumeration {
          enum "enabled";
          enum "disabled";
        }
      }
      leaf publish {
        type enumeration {
          enum "port-profile";
        }
      }
      container inherit {
        leaf port-profile {
          type string;
        }
      }
      container switchport {
        leaf enable {
          tailf:cli-drop-node-name;
          type empty;
        }
        leaf mode {
          type enumeration {
            enum "access";
            enum "trunk";
            enum "dot1q-tunnel";
            enum "fabricpath";
            enum "fex-fabric";
          }
        }
        container access {
          leaf vlan {
            type uint16;
          }
        }
        container trunk {
          container native {
            leaf-list vlan {
              tailf:cli-range-list-syntax;
              type uint16;
            }
          }
          container allowed {
            container vlan {
              choice vlan-choice {
                leaf none {
                  type empty;
                }
                leaf-list ids {
                  tailf:cli-drop-node-name;
                  tailf:cli-range-list-syntax;
                  type vlan-list-type;
                }
              }
            }
          }
        }
        container port-security {
          presence "true";
          leaf maximum {
            type uint16;
          }
        }
      }
      leaf org {
        type string;
      }
      container ip {
        container port {
          leaf access-group {
            type string;
          }
        }
        container verify {
          leaf source {
            type enumeration {
              enum "dhcp-snooping-vlan";
            }
          }
        }
      }
      container vn-service {
        tailf:cli-compact-syntax;
        leaf ip-address {
          type inet:ipv4-address;
        }
        leaf l3-mode {
          type empty;
        }
        leaf security-profile {
          type string;
        }
      }
      container channel-group {
        tailf:cli-compact-syntax;
        tailf:cli-sequence-commands;
        leaf auto {
          type empty;
        }
        leaf mode {
          type enumeration {
            enum "on";
            enum "off";
          }
        }
        leaf mac-pinning {
          type empty;
        }
      }
      container system {
        leaf vlan {
          type uint16;
        }
      }
      leaf mtu {
        type uint16;
      }
      list load-interval {
        tailf:cli-suppress-mode;
        tailf:cli-delete-when-empty;
        key "counter";
        leaf counter {
          tailf:cli-expose-key-name;
          type uint8;
        }
        leaf delay {
          tailf:cli-drop-node-name;
          type uint16;
        }
      }
      container cdp {
        leaf enable {
          type boolean;
        }
      }
      container spanning-tree {
        container port {
          tailf:cli-sequence-commands {
            tailf:cli-reset-siblings;
          }
          tailf:cli-compact-syntax;
          leaf type {
            type enumeration {
              enum "edge";
              enum "network";
              enum "normal";
            }
          }
          leaf trunk {
            type empty;
          }
        }
        leaf port-priority {
          type uint8;
        }
      }
      list service-policy {
        tailf:cli-suppress-mode;
        tailf:cli-delete-when-empty;
        tailf:cli-compact-syntax;
        tailf:cli-sequence-commands {
          tailf:cli-reset-siblings;
        }
        key "type direction";
        leaf type {
          tailf:cli-expose-key-name;
          type enumeration {
            enum "qos";
            enum "queuing";
          }
        }
        leaf direction {
          type enumeration {
            enum "input";
            enum "output";
          }
        }
        leaf policy-map {
          tailf:cli-drop-node-name;
          type string;
        }
        leaf no-stats {
          type empty;
        }
      }
      leaf port-type {
        type string;
      }
      container encapsulation {
        container mpls {
          tailf:cli-add-mode;
          presence "true";
        }
      }
    }
  }
  container configure {
    container maintenance {
      container profile {
        container maintenance-mode {
          tailf:cli-add-mode;
          presence "true";
          uses maintenance-mode-grouping;
        }
        container normal-mode {
          tailf:cli-add-mode;
          presence "true";
          uses maintenance-mode-grouping;
        }
      }
    }
  }

  grouping maintenance-mode-grouping {
    container system {
      container interface {
        leaf shutdown {
          type boolean;
        }
      }
    }
    container router {
      list bgp {
        key "id";
        leaf id {
          type string;
        }
        leaf isolate {
          type empty;
        }
        container template {
          tailf:cli-compact-syntax;
          list peer {
            key "name";
            leaf name {
              type string;
            }
            uses template-neighbor-common-grouping;
            leaf remote-as {
              type asn-type;
            }
          }
        }
      }
      list ospf {
        key "id";
        leaf id {
          tailf:cli-suppress-range;
          type ospf-id-type;
        }
        leaf isolate {
          type empty;
        }
      }
    }
  }

  container system {
    leaf-list bridge-domain {
      tailf:cli-range-list-syntax;
      type uint16;
    }
    container vlan {
      leaf long-name {
        type empty;
      }
      container nve-overlay {
        leaf-list id {
          tailf:cli-range-list-syntax;
          type uint16;
        }
      }
    }
    container storage-loss {
      container log {
        leaf time {
          type uint16;
        }
      }
    }
    container qos {
      tailf:cli-add-mode;
      container service-policy {
        container type {
          leaf network-qos {
            type policy-map-name-type;
          }
          container qos {
            leaf input {
              type policy-map-name-type;
            }
          }
          container queuing {
            leaf input {
              type policy-map-name-type;
            }
            leaf output {
              type policy-map-name-type;
            }
          }
        }
      }
    }
    container auto-upgrade {
      leaf epld {
        type empty;
      }
    }
    leaf-list module-type {
      tailf:cli-flat-list-syntax;
      type module-type;
    }
    leaf jumbomtu {
      type uint16;
    }
    container urpf {
      leaf disable {
        type empty;
      }
    }
    container module {
      container failure-action {
        leaf shutdown {
          type empty;
        }
      }
    }
    container nve {
      leaf-list infra-vlans {
        tailf:cli-range-list-syntax;
        type uint16;
      }
    }
    container interface {
      leaf shutdown {
        type empty;
      }
    }
    container mode {
      container maintenance {
        presence "true";
        leaf shutdown {
          type empty;
        }
      }
    }
    leaf admin-vdc {
      type empty;
    }
    container default {
      leaf switchport {
        type boolean;
      }
      container switchport-config {
        tailf:cli-drop-node-name;
        container switchport {
          leaf shutdown {
            type boolean;
          }
          leaf fabricpath {
            type empty;
          }
        }
      }
      container zone {
        container smart-zone {
          leaf enable {
            type empty;
          }
        }
      }
    }
    container routing {
      leaf unknown-unicast-flood {
        type boolean;
      }
      leaf template {
        tailf:cli-drop-node-name;
        type enumeration {
          enum "template-dual-stack-host-scale";
          enum "template-internet-peering";
          enum "template-lpm-heavy";
          enum "template-mpls-heavy";
          enum "template-multicast-heavy";
        }
      }
    }
    container vrf-member-change {
      leaf retain-l3-config {
        type empty;
      }
    }
    container dot1q-tunnel {
      container transit {
        presence "true";
        leaf vlan {
          type uint16;
        }
      }
    }
    container login {
      container block-for {
        tailf:cli-compact-syntax;
        tailf:cli-sequence-commands {
          tailf:cli-reset-siblings;
        }
        leaf time {
          tailf:cli-drop-node-name;
          type uint16;
        }
        leaf attempts {
          type uint16;
        }
        leaf within {
          type uint16;
        }
      }
      container quiet-mode {
        leaf access-class {
          type string;
        }
      }
    }
  }
  list bridge-domain {
    key "id";
    leaf id {
      type uint16;
    }
    container member {
      leaf vni {
        type uint32;
      }
    }
    uses vlan-bd-config-grouping;
  }
  container vdc {
    list vdc-list {
      tailf:cli-drop-node-name;
      key "name id";
      leaf name {
        type string;
      }
      leaf id {
        tailf:cli-expose-key-name;
        type uint16;
      }
      uses vdc-grouping;
      leaf cpu-share {
        type uint8;
      }
      container allow {
        container feature-set {
          uses feature-set-grouping;
        }
      }
      container allocate {
        list interface {
          key "name";
          leaf name {
            type string;
          }
        }
      }
      leaf boot-order {
        type uint8;
      }
    }
    container resource {
      list template {
        key "name";
        leaf name {
          type string;
        }
        uses vdc-grouping;
      }
    }
    leaf combined-hostname {
      type boolean;
    }
  }
  container policy-map {
    container type {
      list control-plane {
        key "name";
        leaf name {
          type string;
        }
        list class {
          key "name";
          leaf name {
            type class-name-type;
          }
          uses policy-map-class-qos-grouping;
          container logging {
            container drop {
              tailf:cli-compact-syntax;
              tailf:cli-sequence-commands {
                tailf:cli-reset-siblings;
              }
              leaf threshold {
                type uint64;
              }
              leaf level {
                type uint8;
              }
            }
          }
        }
      }
      list qos {
        key "name";
        leaf name {
          type policy-map-name-type;
        }
        leaf description {
          tailf:cli-multi-value;
          type string;
        }
        list class {
          ordered-by user;
          key "name";
          leaf name {
            type class-name-type;
          }
          uses policy-map-class-qos-grouping;
        }
      }
      list network-qos {
        key "name";
        leaf name {
          type policy-map-name-type;
        }
        leaf description {
          tailf:cli-multi-value;
          type string;
        }
        container class {
          container type {
            list network-qos {
              key "name";
              leaf name {
                type class-name-type;
              }
              container dpp {
                leaf set-qos-group {
                  type uint8;
                }
              }
              leaf mtu {
                type uint16;
              }
              leaf multicast-optimize {
                type empty;
              }
              container pause {
                container no-drop {
                  presence "Enable no-drop for the CoS";
                  tailf:cli-compact-syntax;
                  tailf:cli-sequence-commands {
                    tailf:cli-reset-all-siblings;
                  }
                  leaf buffer-size {
                    tailf:cli-optional-in-sequence;
                    type uint32;
                  }
                  leaf pause-threshold {
                    type uint32;
                  }
                  leaf resume-threshold {
                    type uint32;
                  }
                  leaf-list pfc-cos {
                    tailf:cli-range-list-syntax;
                    type uint8;
                  }
                }
              }
              container queue-limit {
                tailf:cli-compact-syntax;
                tailf:cli-sequence-commands;
                leaf count {
                  tailf:cli-drop-node-name;
                  type uint32;
                }
                leaf bytes {
                  type empty;
                }
              }
              container set {
                leaf cos {
                  type uint8;
                }
              }
            }
          }
        }
      }
      list queuing {
        key "name";
        leaf name {
          type policy-map-name-type;
        }
        leaf description {
          tailf:cli-multi-value;
          type string;
        }
        container class {
          container type {
            list queuing {
              key "name";
              leaf name {
                type class-name-type;
              }
              container afd {
                tailf:cli-compact-syntax;
                tailf:cli-sequence-commands {
                  tailf:cli-reset-siblings;
                }
                leaf queue-desired {
                  type uint32;
                }
                leaf unit {
                  tailf:cli-drop-node-name;
                  type enumeration {
                    enum "bytes";
                    enum "kbytes";
                    enum "mbytes";
                  }
                }
                leaf ecn {
                  type empty;
                }
              }
              container bandwidth {
                container remaining {
                  leaf percent {
                    type uint8;
                  }
                }
                leaf percent {
                  type uint8;
                }
              }
              container priority {
                leaf level {
                  type uint8;
                }
              }
              container queue-limit {
                tailf:cli-compact-syntax;
                tailf:cli-sequence-commands {
                  tailf:cli-reset-siblings;
                }
                uses queue-limit-grouping;
              }
              container queue-limit-per-cos {
                tailf:cli-drop-node-name;
                list queue-limit {
                  tailf:cli-suppress-mode;
                  tailf:cli-delete-when-empty;
                  tailf:cli-compact-syntax;
                  tailf:cli-sequence-commands {
                    tailf:cli-reset-siblings;
                  }
                  key "cos";
                  leaf cos {
                    tailf:cli-expose-key-name;
                    type uint8;
                  }
                  uses queue-limit-grouping;
                }
              }
              container shape {
                container average {
                  choice shape-type {
                    case bit-rate {
                      leaf rate {
                        tailf:cli-drop-node-name;
                        must "../unit";
                        type uint32;
                      }
                      leaf unit {
                        type enumeration {
                          enum "bps";
                          enum "gbps";
                          enum "kbps";
                          enum "mbps";
                        }
                      }
                    }
                    case percent {
                      leaf percent {
                        type uint8;
                      }
                    }
                  }
                }
                container min-max {
                  tailf:cli-drop-node-name;
                  tailf:cli-compact-syntax;
                  tailf:cli-sequence-commands {
                    tailf:cli-reset-siblings;
                  }
                  leaf min {
                    type uint64;
                  }
                  leaf min-unit {
                    tailf:cli-drop-node-name;
                    tailf:cli-optional-in-sequence;
                    type enumeration {
                      enum "bps";
                      enum "gbps";
                      enum "kbps";
                      enum "mbps";
                      enum "pps";
                    }
                  }
                  leaf max {
                    type uint64;
                  }
                  leaf max-unit {
                    tailf:cli-drop-node-name;
                    type enumeration {
                      enum "bps";
                      enum "gbps";
                      enum "kbps";
                      enum "mbps";
                      enum "pps";
                    }
                  }
                }
              }
              container random-detect {
                container cos-based {
                  presence "true";
                }
              }
              container random-detect-wred {
                tailf:cli-drop-node-name;
                choice threshold-choice {
                  list random-detect {
                    tailf:cli-suppress-mode;
                    tailf:cli-delete-when-empty;
                    tailf:cli-compact-syntax;
                    tailf:cli-sequence-commands {
                      tailf:cli-reset-siblings;
                    }
                    key "cos";
                    leaf cos {
                      tailf:cli-expose-key-name;
                      type uint8;
                    }
                    uses random-detect-grouping;
                  }
                  container random-detect-no-cos {
                    tailf:cli-drop-node-name;
                    container random-detect {
                      tailf:cli-sequence-commands {
                        tailf:cli-reset-siblings;
                      }
                      tailf:cli-compact-syntax;
                      uses random-detect-grouping;
                      leaf drop-probability {
                        type uint8;
                      }
                      leaf weight {
                        type uint8;
                      }
                    }
                  }
                  container random-detect-threshold {
                    tailf:cli-drop-node-name;
                    container random-detect {
                      container threshold {
                        tailf:cli-sequence-commands {
                          tailf:cli-reset-siblings;
                        }
                        tailf:cli-compact-syntax;
                        leaf type {
                          tailf:cli-drop-node-name;
                          type enumeration {
                            enum "burst-optimized";
                            enum "mesh-optimized";
                          }
                        }
                        leaf ecn {
                          type empty;
                        }
                      }
                    }
                  }
                }
              }
            }
          }
        }
      }
    }
  }
  container advertise {
    container evpn {
      leaf multicast {
        type empty;
      }
    }
  }
  container encapsulation {
    container profile {
      list vni {
        key "name";
        leaf name {
          type string;
        }
        list dot1q {
          tailf:cli-suppress-mode;
          tailf:cli-delete-when-empty;
          key "vlan-id";
          leaf vlan-id {
            type uint16;
          }
          leaf vni {
            type uint32;
          }
        }
        container untagged {
          leaf vni {
            type uint32;
          }
        }
      }
    }
    container vni {
      container dynamic {
        container dot1q {
          tailf:cli-compact-syntax;
          tailf:cli-sequence-commands;
          leaf-list vlan-id {
            tailf:cli-drop-node-name;
            tailf:cli-range-list-syntax;
            type uint16;
          }
        }
      }
    }
  }
  container l2vpn {
    tailf:cli-add-mode;
    container logging {
      container pseudowire {
        leaf status {
          type empty;
        }
      }
      leaf redundancy {
        type empty;
      }
    }
    leaf router-id {
      type inet:ipv4-address;
    }
    leaf sanity {
      type empty;
    }
    leaf shutdown {
      type empty;
    }
    container vfi {
      container redundancy {
        container delay {
          tailf:cli-compact-syntax;
          tailf:cli-sequence-commands {
            tailf:cli-reset-siblings;
          }
          leaf init-wait {
            type uint16;
          }
          leaf pw-wait {
            type uint16;
          }
        }
      }
    }
  }
  container l2vpn-xconnect {
    tailf:cli-drop-node-name;
    container l2vpn {
      container xconnect {
        list context {
          key "name";
          leaf name {
            type string;
          }
          leaf description {
            tailf:cli-multi-value;
            type string;
          }
          leaf interworking {
            type enumeration {
              enum "ethernet";
              enum "vlan";
            }
          }
          container member {
            list vc-member {
              tailf:cli-drop-node-name;
              tailf:cli-suppress-mode;
              tailf:cli-delete-when-empty;
              tailf:cli-compact-syntax;
              tailf:cli-sequence-commands {
                tailf:cli-reset-siblings;
              }
              key "address vc-id";
              leaf address {
                type inet:ipv4-address;
              }
              leaf vc-id {
                type uint32;
              }
              choice enc-or-prof {
                leaf encapsulation {
                  type enumeration {
                    enum "mpls";
                  }
                }
                leaf port-profile {
                  type string;
                }
              }
              leaf group {
                type string;
              }
              leaf priority {
                type uint8;
              }
            }
            list if-member {
              tailf:cli-drop-node-name;
              tailf:cli-suppress-mode;
              tailf:cli-delete-when-empty;
              tailf:cli-compact-syntax;
              tailf:cli-sequence-commands {
                tailf:cli-reset-siblings;
              }
              key "interface";
              leaf interface {
                type string;
              }
              leaf address {
                tailf:cli-drop-node-name;
                tailf:cli-optional-in-sequence;
                type inet:ipv4-address;
              }
              leaf vc-id {
                tailf:cli-drop-node-name;
                type uint32;
              }
              choice enc-or-prof {
                leaf encapsulation {
                  type enumeration {
                    enum "mpls";
                  }
                }
                leaf port-profile {
                  type string;
                }
              }
              leaf service-instance {
                tailf:cli-optional-in-sequence;
                type uint16;
              }
              leaf group {
                type string;
              }
              leaf priority {
                type uint8;
              }
            }
          }
          container redundancy {
            tailf:cli-compact-syntax;
            tailf:cli-sequence-commands {
              tailf:cli-reset-siblings;
            }
            leaf delay {
              type uint8;
            }
            leaf disable {
              tailf:cli-drop-node-name;
              type union {
                type uint8;
                type enumeration {
                  enum "never";
                }
              }
            }
            leaf group {
              type string;
            }
          }
          container remote {
            container link {
              container failure {
                leaf notification {
                  type boolean;
                }
              }
            }
          }
          leaf shutdown {
            type empty;
          }
        }
      }
    }
  }
  list slot {
    key "number";
    leaf number {
      type uint8;
    }
    container provision {
      leaf model {
        type union {
          type enumeration {
            enum "N2K-B22DELL";
            enum "N2K-B22FJ";
            enum "N2K-B22HP";
            enum "N2K-B22IBM";
            enum "N2K-C2148T";
            enum "N2K-C2232P";
            enum "N2K-C2232TM";
            enum "N2K-C2232TM-E-10GE";
            enum "N2K-C2248GV+P";
            enum "N2K-C2248PQ";
            enum "N2K-C2248T";
            enum "N2K-C2248TP-E-1GE";
            enum "N2K-C2332TQ";
            enum "N2K-C2348TQ";
            enum "N2K-C2348UPQ";
            enum "N2K-N2224TP";
            enum "N55-M12T";
            enum "N55-M16FP";
            enum "N55-M16P";
            enum "N55-M16UP";
            enum "N55-M4EP40G";
            enum "N55-M4Q";
            enum "N55-M8P8FP";
            enum "N56-M24UP2Q";
            enum "N5600-12Q-FIX";
            enum "N5600-48Q-12Q-FIX";
            enum "N5600-M12Q";
            enum "N5696-M12Q";
            enum "N5696-M4C";
            enum "N5K-M1008";
            enum "N5K-M1060";
            enum "N5K-M1404";
            enum "N5K-M1600";
            enum "N5K-N5696-M20UP";
            enum "N6004-M12Q";
            enum "N6K-C6004-M12Q";
            enum "N6K-C6004X-M20UP";
          }
          type string;
        }
      }
    }
    list port {
      tailf:cli-suppress-mode;
      tailf:cli-delete-when-empty;
      key "range";
      leaf range {
        type string;
      }
      leaf type {
        type enumeration {
          enum "ethernet";
          enum "fc";
        }
      }
    }
  }
  container interface {
    list breakout {
      tailf:cli-suppress-mode;
      tailf:cli-delete-when-empty;
      tailf:cli-compact-syntax;
      tailf:cli-sequence-commands {
        tailf:cli-reset-siblings;
      }
      key "module port";
      leaf module {
        tailf:cli-expose-key-name;
        type uint8;
      }
      leaf port {
        tailf:cli-expose-key-name;
        type uint16;
      }
      leaf map {
        type enumeration {
          enum "10g-4x";
          enum "25g-4x";
          enum "50g-2x";
          enum "50g-4x";
          enum "100g-2x";
          enum "100g-2x-pam4";
          enum "100g-4x";
          enum "200g-2x";
        }
      }
    }
    list mgmt {
      tailf:cli-allow-join-with-key;
      key "name";
      leaf name {
        type uint16;
      }
      leaf shutdown {
        type empty;
      }
      container shutdown-force {
        tailf:cli-drop-node-name;
        container shutdown {
          leaf force {
            type empty;
          }
        }
      }
      uses interface-common-grouping {
        augment "ipv6" {
          uses interface-ip-flow-grouping;
        }
        augment "ip" {
          uses interface-ip-flow-grouping;
        }
      }
      uses interface-eth-and-mgmt-grouping;
      container snmp {
        container trap {
          leaf link-status {
            type boolean;
          }
        }
      }
    }
    container cmp-mgmt {
      list module {
        key "id";
        leaf id {
          type uint8;
        }
        container ip {
          container address {
            tailf:cli-sequence-commands {
              tailf:cli-reset-siblings;
            }
            tailf:cli-compact-syntax;
            leaf ip {
              tailf:cli-drop-node-name;
              type union {
                type tailf:ipv4-address-and-prefix-length;
                type inet:ipv4-address;
              }
            }
            leaf mask {
              tailf:cli-drop-node-name;
              type inet:ipv4-address;
            }
          }
          leaf default-gateway {
            type inet:ipv4-address;
          }
        }
      }
    }
    list Vlan {
      tailf:cli-allow-join-with-key;
      key "name";
      leaf name {
        type uint16;
      }
      leaf shutdown {
        type empty;
      }
      container fabricpath {
        leaf domain {
          type string;
        }
        container isis {
          leaf fabric-control {
            type empty;
          }
        }
      }
      uses interface-common-grouping {
        augment "ipv6" {
          leaf forward {
            type empty;
          }
          uses interface-ip-flow-grouping;
        }
        augment "ip" {
          uses interface-ip-flow-grouping;
        }
        refine "vrf/member";
      }
      uses interface-bfd-grouping;
      uses interface-vlan-grouping;
      container private-vlan {
        leaf-list mapping {
          tailf:cli-range-list-syntax;
          type uint16;
        }
      }
    }
    list nve {
      tailf:cli-allow-join-with-key;
      key "name";
      leaf name {
        type uint16;
      }
      leaf auto-remap-replication-servers {
        type empty;
      }
      leaf description {
        tailf:cli-multi-value;
        type string;
      }
      container host-reachability {
        leaf protocol {
          type enumeration {
            enum "bgp";
            enum "openflow";
            enum "openflow-ir";
          }
        }
      }
      container suppress {
        leaf mac-route {
          type empty;
        }
      }
      container global {
        container ingress-replication {
          leaf protocol {
            type enumeration {
              enum "bgp";
            }
          }
        }
        list mcast-group {
          tailf:cli-suppress-mode;
          tailf:cli-delete-when-empty;
          tailf:cli-compact-syntax;
          tailf:cli-sequence-commands {
            tailf:cli-reset-siblings;
          }
          key "type";
          leaf mcast-addr {
            tailf:cli-drop-node-name;
            tailf:cli-prefix-key;
            type inet:ipv4-address;
          }
          leaf type {
            type enumeration {
              enum "L2";
              enum "L3";
            }
          }
        }
        leaf suppress-arp {
          type empty;
        }
      }
      container member {
        list vni {
          key "id";
          leaf id {
            type union {
              type uint32;
              type string;
            }
          }
          leaf associate-vrf {
            tailf:cli-hide-in-submode;
            type empty;
          }
          leaf vrf {
            tailf:cli-hide-in-submode;
            type string;
          }
          leaf mcast-group {
            type inet:ipv4-address;
          }
          container host-reachability {
            leaf protocol {
              type enumeration {
                enum "bgp";
              }
            }
          }
          leaf suppress-arp {
            type empty;
          }
          leaf suppress-unknown-unicast {
            type empty;
          }
          container ingress-replication {
            container protocol {
              leaf bgp {
                type empty;
              }
              container static {
                tailf:cli-add-mode;
                presence "true";
                list peer-ip {
                  tailf:cli-suppress-mode;
                  tailf:cli-delete-when-empty;
                  key "ip";
                  leaf ip {
                    type inet:ipv4-address;
                  }
                }
              }
            }
          }
          container multisite {
            container ingress-replication {
              tailf:cli-delete-when-empty;
              presence "true";
              leaf optimized {
                type empty;
              }
            }
            leaf mcast-group {
              type inet:ipv4-address;
            }
          }
        }
      }
      container multisite {
        leaf virtual-rmac {
          type string;
        }
        container border-gateway {
          leaf interface {
            type string;
          }
        }
      }
      leaf overlay-encapsulation {
        type enumeration {
          enum "vxlan";
          enum "vxlan-with-tag";
        }
      }
      leaf remap-replication-servers {
        type empty;
      }
      leaf replication-server {
        type inet:ipv4-address;
      }
      leaf shutdown {
        type empty;
      }
      container source-interface {
        tailf:cli-compact-syntax;
        tailf:cli-sequence-commands {
          tailf:cli-reset-siblings;
        }
        leaf name {
          tailf:cli-drop-node-name;
          type string;
        }
        leaf anycast {
          type string;
        }
      }
      container source-interface-cfg {
        tailf:cli-drop-node-name;
        container source-interface {
          leaf hold-down-time {
            type uint16;
          }
        }
      }
      container fabric-ready {
        leaf time {
          type uint16;
        }
      }
      container mcast-routing {
        container override {
          leaf source-interface {
            type string;
          }
        }
      }
      container advertise {
        leaf virtual-rmac {
          type empty;
        }
      }
      container qos-mode {
        leaf pipe {
          type empty;
        }
      }
      uses if-service-policy-grouping;
    }
    list Vethernet {
      tailf:cli-allow-join-with-key;
      key "name";
      leaf name {
        type string;
      }
      uses interface-switchport-grouping;
      leaf shutdown {
        type empty;
      }
      uses interface-common-grouping;
      uses interface-ethernet-grouping;
      container vmware {
        container dvport {
          tailf:cli-compact-syntax;
          tailf:cli-sequence-commands {
            tailf:cli-reset-siblings;
          }
          leaf port {
            tailf:cli-drop-node-name;
            type uint32;
          }
          leaf dvswitch {
            type empty;
          }
          leaf uuid {
            type string;
          }
        }
        container vm {
          tailf:cli-compact-syntax;
          tailf:cli-sequence-commands {
            tailf:cli-reset-siblings;
          }
          leaf mac {
            type string;
          }
        }
      }
      container dvport {
        leaf uuid {
          type string;
        }
      }
    }
    list Bdi {
      tailf:cli-allow-join-with-key;
      key "name";
      leaf name {
        type uint16;
      }
      leaf shutdown {
        type empty;
      }
      uses interface-common-grouping {
        augment "ipv6" {
          leaf forward {
            type empty;
          }
        }
        refine "vrf/member";
      }
      uses interface-vlan-grouping;
    }
    list port-channel {
      tailf:cli-allow-join-with-key;
      key "name";
      leaf name {
        type string;
      }
      uses interface-switchport-grouping {
        refine "switchport";
      }
      leaf shutdown {
        type empty;
      }
      uses interface-common-grouping {
        refine "ip/unnumbered";
        augment "ipv6" {
          uses interface-ip-flow-grouping;
        }
        augment "ip" {
          uses interface-ip-flow-grouping;
        }
      }
      uses interface-ethernet-grouping;
      uses ethernet-and-port-channel-grouping;
      uses interface-eth-pc-bfd-grouping;
      uses interface-port-channel-grouping;
      uses interface-l2port-common-grouping;
    }
    list Ethernet {
      tailf:cli-allow-join-with-key;
      key "name";
      leaf name {
        type string;
      }
      uses interface-switchport-grouping {
        augment "switchport" {
          container voice {
            leaf vlan {
              type union {
                type uint16;
                type enumeration {
                  enum "dot1p";
                  enum "untagged";
                }
              }
            }
          }
        }
      }
      container lacp {
        leaf port-priority {
          type uint16;
        }
        leaf rate {
          type enumeration {
            enum "fast";
            enum "normal";
          }
        }
      }
      container channel-group {
        tailf:cli-compact-syntax;
        tailf:cli-sequence-commands {
          tailf:cli-reset-siblings;
        }
        leaf id {
          tailf:cli-drop-node-name;
          type uint16;
        }
        leaf mode {
          type enumeration {
            enum "active";
            enum "on";
            enum "passive" {
              tailf:code-name "mode_passive";
            }
          }
        }
      }
      leaf beacon {
        type empty;
      }
      container link {
        container debounce {
          presence "true";
          leaf time {
            type uint16;
          }
          container link-up {
            leaf time {
              type uint16;
            }
          }
        }
      }
      leaf speed-group {
        type enumeration {
          enum "10000";
          enum "40000";
        }
      }
      leaf fec {
        type enumeration {
          enum "auto";
          enum "cl74";
          enum "cl91";
          enum "fc-fec";
          enum "rs-cons16";
          enum "rs-fec";
          enum "rs-ieee";
          enum "off";
        }
      }
      container eapol {
        tailf:cli-compact-syntax;
        tailf:cli-sequence-commands;
        leaf mac-address {
          type union {
            type mac-address-type;
            type enumeration {
              enum "broadcast-address";
            }
          }
        }
        leaf ethertype {
          type string;
        }
      }
      leaf shutdown {
        type empty;
      }
      uses interface-common-grouping {
        refine "vrf/member";
        refine "ip/unnumbered";
        augment "ipv6" {
          uses interface-ip-flow-grouping;
        }
        augment "ip" {
          uses interface-ip-flow-grouping;
        }
      }
      uses interface-ethernet-grouping {
        augment "evpn" {
          container multihoming {
            leaf core-tracking {
              type empty;
            }
          }
        }
      }
      uses ethernet-and-port-channel-grouping;
      uses interface-eth-pc-bfd-grouping;
      uses interface-eth-and-mgmt-grouping;
      uses interface-vrrpv3-grouping;
      leaf udld {
        type enumeration {
          enum "aggressive";
          enum "disable";
          enum "enable";
        }
      }
      container mdix {
        leaf auto {
          type boolean;
        }
      }
      container ptp {
        presence "true";

        grouping if-ptp-val-grouping {
          leaf interval {
            tailf:cli-drop-node-name;
            type int8;
          }
          leaf aes67 {
            type int8;
          }
          leaf smpte-2059-2 {
            type int8;
          }
        }
        container announce {
          container interval {
            uses if-ptp-val-grouping;
          }
          container timeout {
            uses if-ptp-val-grouping;
          }
        }
        container delay-request {
          container minimum {
            container interval {
              uses if-ptp-val-grouping;
            }
          }
        }
        container multicast {
          leaf master-only {
            type empty;
          }
        }
        container sync {
          container interval {
            uses if-ptp-val-grouping;
          }
        }
        leaf vlan {
          type uint16;
        }
      }
      container frequency {
        container synchronization {
          tailf:cli-add-mode;
          presence "true";
          leaf priority {
            type uint8;
          }
          container quality {
            container receive {
              tailf:cli-compact-syntax;
              tailf:cli-sequence-commands {
                tailf:cli-reset-siblings;
              }
              uses itu-t-grouping;
            }
            container transmit {
              tailf:cli-compact-syntax;
              tailf:cli-sequence-commands {
                tailf:cli-reset-siblings;
              }
              uses itu-t-grouping;
            }
          }
          container selection {
            leaf input {
              type empty;
            }
          }
          container ssm {
            leaf disable {
              type empty;
            }
          }
          leaf wait-to-restore {
            type uint8;
          }
        }
      }
      container dot1x {
        leaf pae {
          type enumeration {
            enum "authenticator";
          }
        }
        leaf host-mode {
          type enumeration {
            enum "multi-auth";
            enum "multi-host";
            enum "single-host";
          }
        }
        container mac-auth-bypass {
          presence "true";
          leaf eap {
            type empty;
          }
        }
        leaf max-reauth-req {
          type uint8;
        }
        leaf max-req {
          type uint8;
        }
        leaf port-control {
          type enumeration {
            enum "auto";
            enum "force-authorized";
            enum "force-unauthorized";
          }
        }
        leaf re-authentication {
          type boolean;
        }
        container timeout {
          leaf inactivity-period {
            type uint32;
          }
          leaf quiet-period {
            type uint16;
          }
          leaf ratelimit-period {
            type uint16;
          }
          leaf re-authperiod {
            type uint32;
          }
          leaf server-timeout {
            type uint16;
          }
          leaf supp-timeout {
            type uint16;
          }
          leaf tx-period {
            type uint16;
          }
        }
      }
      container macsec {
        tailf:cli-compact-syntax;
        tailf:cli-sequence-commands {
          tailf:cli-reset-siblings;
        }
        leaf keychain {
          type string;
        }
        leaf policy {
          type string;
        }
        leaf fallback-keychain {
          type string;
        }
      }
    }
    list fc {
      tailf:cli-allow-join-with-key;
      key "name";
      leaf name {
        type string;
      }
      uses interface-switchport2-grouping {
        augment "switchport" {
          leaf beacon {
            type empty;
          }
          container fcrxbbcredit {
            choice bbcredit-choice {
              container creds {
                tailf:cli-drop-node-name;
                leaf credit {
                  tailf:cli-drop-node-name;
                  type uint8;
                }
                container ecreds {
                  tailf:cli-drop-node-name;
                  tailf:cli-compact-syntax;
                  tailf:cli-sequence-commands {
                    tailf:cli-reset-siblings;
                  }
                  presence "true";
                  leaf credit {
                    tailf:cli-drop-node-name;
                    type uint8;
                  }
                  leaf mode {
                    type enumeration {
                      enum "E";
                    }
                  }
                }
                container fcreds {
                  tailf:cli-drop-node-name;
                  tailf:cli-compact-syntax;
                  tailf:cli-sequence-commands {
                    tailf:cli-reset-siblings;
                  }
                  presence "true";
                  leaf credit {
                    tailf:cli-drop-node-name;
                    type uint8;
                  }
                  leaf mode {
                    type enumeration {
                      enum "Fx";
                    }
                  }
                }
              }
              leaf default {
                type empty;
              }
            }
          }
          container ignore {
            leaf bit-errors {
              type empty;
            }
          }
        }
      }
      container channel-group {
        choice channel-group-choice {
          list port {
            tailf:cli-drop-node-name;
            tailf:cli-compact-syntax;
            tailf:cli-sequence-commands {
              tailf:cli-reset-siblings;
            }
            key "nr";
            leaf nr {
              type uint16;
            }
            leaf force {
              type empty;
            }
          }
          leaf auto {
            type empty;
          }
        }
      }
      container out-of-service {
        presence "Put an interface out of service.";
        leaf force {
          type empty;
        }
      }
      leaf link-state-trap {
        type empty;
      }
      uses interface-fc-and-san-grouping {
        refine "shutdown";
      }
    }
    list vfc {
      tailf:cli-allow-join-with-key;
      key "id";
      leaf id {
        type uint16;
      }
      container bind {
        choice bind-choice {
          container interface {
            choice eth-or-po {
              leaf Ethernet {
                tailf:cli-allow-join-with-value;
                type string;
              }
              leaf port-channel {
                tailf:cli-allow-join-with-value;
                type string;
              }
            }
          }
          leaf mac-address {
            type mac-address-type;
          }
        }
      }
      container switchport {
        leaf description {
          tailf:cli-multi-value;
          type string;
        }
        leaf mode {
          type enumeration {
            enum "F";
            enum "NP";
          }
        }
        container trunk {
          container allowed {
            leaf-list vsan {
              tailf:cli-range-list-syntax;
              type uint16;
            }
          }
        }
      }
      leaf shutdown {
        type empty;
      }
    }
    list loopback {
      tailf:cli-allow-join-with-key;
      key "name";
      leaf name {
        type uint16;
      }
      leaf shutdown {
        type empty;
      }
      uses interface-common-grouping;
    }
    list control {
      tailf:cli-allow-join-with-key;
      key "name";
      leaf name {
        type uint16;
      }
      leaf shutdown {
        type empty;
      }
      uses interface-common-grouping;
    }
    list san-port-channel {
      tailf:cli-allow-join-with-key;
      key "name";
      leaf name {
        type uint16;
      }
      uses interface-switchport2-grouping;
      container channel {
        leaf mode {
          type enumeration {
            enum "active";
          }
        }
      }
      uses interface-fc-and-san-grouping;
    }
    list data {
      tailf:cli-allow-join-with-key;
      key "name";
      leaf name {
        type uint16;
      }
      leaf shutdown {
        type empty;
      }
      uses interface-common-grouping;
    }
    list Tunnel {
      tailf:cli-allow-join-with-key;
      key "name";
      leaf name {
        type uint16;
      }
      leaf shutdown {
        type empty;
      }
      uses interface-common-grouping {
        refine "vrf/member";
        augment "ipv6" {
          uses interface-ip-flow-grouping;
        }
        augment "ip" {
          uses interface-ip-flow-grouping;
        }
      }
      container tunnel {
        leaf destination {
          type union {
            type inet:ipv4-address;
            type string;
          }
        }
        leaf source {
          type union {
            type inet:ipv4-address;
            type string;
          }
        }
      }
      leaf mtu {
        type uint16;
      }
      leaf bandwidth {
        type uint32;
      }
    }
    list Overlay {
      tailf:cli-allow-join-with-key;
      key "id";
      leaf id {
        type uint16;
      }
      leaf description {
        tailf:cli-multi-value;
        type string;
      }
      container otv {
        container adjacency-server {
          leaf unicast-only {
            type empty;
          }
        }
        container arp-nd {
          leaf timeout {
            type uint32;
          }
        }
        leaf broadcast-group {
          type inet:ipv4-address;
        }
        leaf control-group {
          type inet:ipv4-address;
        }
        leaf-list data-group {
          tailf:cli-flat-list-syntax;
          type tailf:ipv4-address-and-prefix-length;
        }
        leaf-list extend-vlan {
          tailf:cli-range-list-syntax;
          type uint16;
        }
        container isis {
          container authentication {
            leaf key-chain {
              type string;
            }
          }
          leaf authentication-check {
            type boolean;
          }
          leaf authentication-type {
            type enumeration {
              enum "cleartext";
              enum "md5";
            }
          }
          leaf csnp-interval {
            type uint16;
          }
          leaf hello-interval {
            type uint16;
          }
          leaf hello-multiplier {
            type uint16;
          }
          leaf hello-padding {
            type boolean;
          }
          leaf lsp-interval {
            type uint16;
          }
          leaf metric {
            type uint32;
          }
          leaf priority {
            type uint8;
          }
        }
        leaf join-interface {
          type string;
        }
        leaf suppress-arp-nd {
          type boolean;
        }
        container use-adjacency-server {
          tailf:cli-compact-syntax;
          tailf:cli-sequence-commands {
            tailf:cli-reset-siblings;
          }
          leaf primary-address {
            tailf:cli-drop-node-name;
            type union {
              type inet:ipv4-address;
              type inet:ipv6-address;
            }
          }
          leaf secondary-address {
            tailf:cli-drop-node-name;
            tailf:cli-optional-in-sequence;
            type union {
              type inet:ipv4-address;
              type inet:ipv6-address;
            }
          }
          leaf unicast-only {
            type empty;
          }
        }
      }
      leaf shutdown {
        type empty;
      }
    }
    list pseudowire {
      tailf:cli-allow-join-with-key;
      key "id";
      leaf id {
        type uint32;
      }
      leaf description {
        tailf:cli-multi-value;
        type string;
      }
      container encapsulation {
        container mpls {
          tailf:cli-add-mode;
          presence "true";
        }
      }
      container inherit {
        leaf port-profile {
          type string;
        }
      }
      leaf mtu {
        type uint16;
      }
      container neighbor {
        tailf:cli-compact-syntax;
        tailf:cli-sequence-commands {
          tailf:cli-reset-siblings;
        }
        leaf address {
          tailf:cli-drop-node-name;
          type inet:ipv4-address;
        }
        leaf vc-id {
          tailf:cli-drop-node-name;
          type uint32;
        }
      }
      leaf shutdown {
        type empty;
      }
      container signaling {
        leaf protocol {
          type enumeration {
            enum "ldp";
            enum "none";
          }
        }
      }
      leaf status {
        type boolean;
      }
      container status-config {
        tailf:cli-drop-node-name;
        container status {
          container control-plane {
            leaf route-watch {
              type boolean;
            }
          }
          leaf decoupled {
            type boolean;
          }
          container peer {
            container topology {
              leaf dual-homed {
                type boolean;
              }
            }
          }
          container redundancy {
            leaf master {
              type boolean;
            }
          }
        }
      }
      container vc {
        leaf type {
          type enumeration {
            enum "ethernet";
            enum "vlan";
          }
        }
      }
    }
  }
  container vsan {
    container database {
      tailf:cli-add-mode;
      list vsan {
        tailf:cli-suppress-mode;
        tailf:cli-delete-when-empty;
        tailf:cli-compact-syntax;
        tailf:cli-sequence-commands {
          tailf:cli-reset-siblings;
        }
        key "id";
        leaf id {
          type uint16;
        }
      }
      container vsan-name {
        tailf:cli-drop-node-name;
        list vsan {
          tailf:cli-suppress-mode;
          key "name";
          leaf id {
            tailf:cli-prefix-key;
            tailf:cli-drop-node-name;
            mandatory true;
            type uint16;
          }
          leaf name {
            tailf:cli-expose-key-name;
            type string;
          }
        }
      }
      container vsan-vfc-binding {
        tailf:cli-drop-node-name;
        list vsan {
          tailf:cli-suppress-mode;
          tailf:cli-sequence-commands;
          key "vfc";
          leaf vfc {
            tailf:cli-expose-key-name;
            tailf:cli-allow-join-with-value;
            type uint16;
          }
          leaf vsan-id {
            tailf:cli-drop-node-name;
            tailf:cli-prefix-key;
            mandatory true;
            type uint16;
          }
          leaf interface {
            tailf:cli-prefix-key;
            mandatory true;
            type empty;
          }
        }
      }
      container vsan-fc-binding {
        tailf:cli-drop-node-name;
        list vsan {
          tailf:cli-suppress-mode;
          tailf:cli-sequence-commands;
          key "fc";
          leaf fc {
            tailf:cli-expose-key-name;
            tailf:cli-allow-join-with-value;
            type string;
          }
          leaf vsan-id {
            tailf:cli-drop-node-name;
            tailf:cli-prefix-key;
            mandatory true;
            type uint16;
          }
          leaf interface {
            tailf:cli-prefix-key;
            mandatory true;
            type empty;
          }
        }
      }
    }
  }
  container device-alias {
    container database {
      tailf:cli-add-mode;
      container device-alias {
        list name {
          tailf:cli-suppress-mode;
          tailf:cli-delete-when-empty;
          key "alias";
          leaf alias {
            type string;
          }
          leaf pwwn {
            type string;
          }
        }
      }
    }
    leaf mode {
      type enumeration {
        enum "enhanced";
      }
    }
  }
  container fcdomain {
    container fcid {
      container database {
        tailf:cli-add-mode;
        list vsan {
          tailf:cli-suppress-mode;
          tailf:cli-delete-when-empty;
          tailf:cli-compact-syntax;
          tailf:cli-sequence-commands {
            tailf:cli-reset-siblings;
          }
          key "wwn";
          leaf wwn {
            tailf:cli-expose-key-name;
            type string;
          }
          leaf vsan-id {
            tailf:cli-drop-node-name;
            tailf:cli-prefix-key;
            type uint16;
          }
          leaf fcid {
            type string;
          }
          leaf area {
            tailf:cli-optional-in-sequence;
            type empty;
          }
          leaf dynamic {
            type empty;
          }
        }
      }
    }
  }
  container zone {
    container smart-zoning {
      container enable {
        list vsan {
          tailf:cli-suppress-mode;
          key "id";
          leaf id {
            type uint16;
          }
        }
      }
    }
    container mode {
      container enhanced {
        list vsan {
          tailf:cli-suppress-mode;
          key "id";
          leaf id {
            type uint16;
          }
        }
      }
    }
    list name {
      key "name vsan";
      leaf name {
        type string;
      }
      leaf vsan {
        tailf:cli-expose-key-name;
        type uint16;
      }
      container member {
        list fwwn {
          tailf:cli-suppress-mode;
          key "wwn";
          leaf wwn {
            type string;
          }
        }
        list pwwn {
          tailf:cli-suppress-mode;
          tailf:cli-sequence-commands {
            tailf:cli-reset-siblings;
          }
          tailf:cli-compact-syntax;
          key "wwn";
          leaf wwn {
            type string;
          }
          leaf type {
            tailf:cli-drop-node-name;
            type enumeration {
              enum "both";
              enum "init";
              enum "target";
            }
          }
        }
        list device-alias {
          tailf:cli-suppress-mode;
          tailf:cli-sequence-commands {
            tailf:cli-reset-siblings;
          }
          tailf:cli-compact-syntax;
          key "name";
          leaf name {
            type string;
          }
          leaf type {
            tailf:cli-drop-node-name;
            type enumeration {
              enum "both";
              enum "init";
              enum "target";
            }
          }
        }
        list fcalias {
          tailf:cli-suppress-mode;
          key "name";
          leaf name {
            type string;
          }
        }
      }
    }
  }
  list fcalias {
    key "name vsan";
    leaf name {
      tailf:cli-expose-key-name;
      type string;
    }
    leaf vsan {
      tailf:cli-expose-key-name;
      type uint16;
    }
    container member {
      list pwwn {
        tailf:cli-suppress-mode;
        tailf:cli-delete-when-empty;
        tailf:cli-compact-syntax;
        tailf:cli-sequence-commands {
          tailf:cli-reset-siblings;
        }
        key "wwn";
        leaf wwn {
          type string;
        }
        leaf type {
          tailf:cli-drop-node-name;
          type enumeration {
            enum "both";
            enum "init";
            enum "target";
          }
        }
      }
    }
  }
  container zoneset {
    list name {
      key "name vsan";
      leaf name {
        type string;
      }
      leaf vsan {
        tailf:cli-expose-key-name;
        type uint16;
      }
      list member {
        tailf:cli-suppress-mode;
        key "name";
        leaf name {
          type string;
        }
      }
    }
    container activate {
      list name {
        tailf:cli-suppress-mode;
        key "name vsan";
        leaf name {
          type string;
        }
        leaf vsan {
          tailf:cli-expose-key-name;
          type uint16;
        }
      }
    }
  }
  container mvr-config {
    tailf:cli-add-mode;
    presence "true";
    container mvr-suppress-query {
      leaf-list vlan {
        tailf:cli-range-list-syntax;
        type uint16;
      }
    }
    uses mvr-cfg-grouping;
  }

  grouping mvr-cfg-grouping {
    list mvr-group {
      tailf:cli-suppress-mode;
      tailf:cli-delete-when-empty;
      tailf:cli-compact-syntax;
      tailf:cli-sequence-commands {
        tailf:cli-reset-siblings;
      }
      key "address";
      leaf address {
        tailf:cli-suppress-range;
        type union {
          type inet:ipv4-address;
          type tailf:ipv4-address-and-prefix-length;
        }
      }
      leaf mask {
        tailf:cli-drop-node-name;
        tailf:cli-optional-in-sequence;
        type inet:ipv4-address;
      }
      leaf count {
        tailf:cli-optional-in-sequence;
        type uint8;
      }
      leaf vlan {
        type uint16;
      }
    }
    leaf mvr-vlan {
      type uint16;
    }
  }

  container otv {
    container site-vlan {
      tailf:cli-add-mode;
      presence "true";
      leaf vlan {
        tailf:cli-drop-node-name;
        tailf:cli-hide-in-submode;
        type uint16;
      }
    }
    leaf site-identifier {
      type union {
        type mac-address-type;
        type string;
      }
    }
  }
  container clock {
    container protocol {
      tailf:cli-compact-syntax;
      tailf:cli-sequence-commands;
      leaf type {
        tailf:cli-drop-node-name;
        type enumeration {
          enum "none";
          enum "ntp";
          enum "ptp";
        }
      }
      leaf vdc {
        type uint8;
      }
    }
    container timezone {
      tailf:cli-compact-syntax;
      tailf:cli-sequence-commands;
      leaf name {
        tailf:cli-drop-node-name;
        type string;
      }
      leaf hours-offset {
        tailf:cli-drop-node-name;
        type int8;
      }
      leaf minutes-offset {
        tailf:cli-drop-node-name;
        type uint8;
      }
    }
    container summer-time {
      tailf:cli-compact-syntax;
      tailf:cli-sequence-commands {
        tailf:cli-reset-siblings;
      }
      leaf tz {
        tailf:cli-drop-node-name;
        type string;
      }
      leaf start-week {
        tailf:cli-drop-node-name;
        type uint8;
      }
      leaf start-day {
        tailf:cli-drop-node-name;
        type string;
      }
      leaf start-month {
        tailf:cli-drop-node-name;
        type string;
      }
      leaf start-time {
        tailf:cli-drop-node-name;
        type string;
      }
      leaf end-week {
        tailf:cli-drop-node-name;
        type uint8;
      }
      leaf end-day {
        tailf:cli-drop-node-name;
        type string;
      }
      leaf end-month {
        tailf:cli-drop-node-name;
        type string;
      }
      leaf end-time {
        tailf:cli-drop-node-name;
        type string;
      }
      leaf offset {
        tailf:cli-drop-node-name;
        type uint8;
      }
    }
    container format {
      container show-timezone {
        leaf debug {
          type empty;
        }
        leaf syslog {
          type empty;
        }
      }
      leaf format {
        tailf:cli-drop-node-name;
        type enumeration {
          enum "12-hours";
          enum "24-hours";
        }
      }
    }
  }
  container object-group {
    container ip {
      list address {
        key "name";
        leaf name {
          type string;
        }
        list sequence {
          tailf:cli-drop-node-name;
          tailf:cli-suppress-mode;
          tailf:cli-delete-when-empty;
          key "id";
          leaf id {
            type uint32;
          }
          choice address-choice {
            leaf host {
              type inet:ipv4-address;
            }
            leaf prefix {
              tailf:cli-drop-node-name;
              type tailf:ipv4-address-and-prefix-length;
            }
            container network-and-mask {
              tailf:cli-drop-node-name;
              tailf:cli-compact-syntax;
              tailf:cli-sequence-commands {
                tailf:cli-reset-siblings;
              }
              leaf address {
                tailf:cli-drop-node-name;
                type inet:ipv4-address;
              }
              leaf mask {
                tailf:cli-drop-node-name;
                type inet:ipv4-address;
              }
            }
          }
        }
      }
      list port {
        key "name";
        leaf name {
          type string;
        }
        list sequence {
          tailf:cli-drop-node-name;
          tailf:cli-suppress-mode;
          tailf:cli-delete-when-empty;
          key "id";
          leaf id {
            tailf:cli-suppress-range;
            type uint32;
          }
          choice port-choice {
            leaf eq {
              type uint16;
            }
            leaf gt {
              type uint16;
            }
            leaf lt {
              type uint16;
            }
            leaf neq {
              type uint16;
            }
            container range {
              tailf:cli-compact-syntax;
              tailf:cli-sequence-commands;
              leaf range-begin {
                tailf:cli-drop-node-name;
                type uint16;
              }
              leaf range-end {
                tailf:cli-drop-node-name;
                type uint16;
              }
            }
          }
        }
      }
    }
    container ipv6 {
      list address {
        key "name";
        leaf name {
          type string;
        }
        list sequence {
          tailf:cli-drop-node-name;
          tailf:cli-suppress-mode;
          tailf:cli-delete-when-empty;
          key "id";
          leaf id {
            type uint32;
          }
          choice address-choice {
            leaf host {
              type inet:ipv6-address;
            }
            leaf prefix {
              tailf:cli-drop-node-name;
              type tailf:ipv6-address-and-prefix-length;
            }
          }
        }
      }
    }
  }
  container cli {
    list alias {
      tailf:cli-suppress-mode;
      tailf:cli-delete-when-empty;
      key "name";
      leaf name {
        tailf:cli-expose-key-name;
        type string;
      }
      leaf line {
        tailf:cli-drop-node-name;
        tailf:cli-multi-value;
        type string;
      }
    }
  }
  container line {
    container console {
      tailf:cli-add-mode;
      uses line-grouping;
      container terminal {
        leaf length {
          type uint16;
        }
        leaf width {
          type uint16;
        }
      }
      leaf parity {
        type enumeration {
          enum "none";
          enum "odd";
          enum "even";
        }
      }
      leaf stopbits {
        type enumeration {
          enum "1";
          enum "1.5";
          enum "2";
        }
      }
    }
    container vty {
      tailf:cli-add-mode;
      presence "true";
      uses line-grouping;
      leaf session-limit {
        type uint8;
      }
      leaf logout-warning {
        type uint8;
      }
    }
  }
  container router {
    list bgp {
      key "id";
      leaf id {
        type string;
      }
      container template {
        tailf:cli-compact-syntax;
        list peer {
          key "name";
          leaf name {
            type string;
          }
          uses template-neighbor-common-grouping;
          leaf remote-as {
            type asn-type;
          }
        }
        list peer-policy {
          key "name";
          leaf name {
            type string;
          }
          uses template-af-common-grouping;
        }
        list peer-session {
          key "name";
          leaf name {
            type string;
          }
          uses template-base-grouping;
          choice egress-eng-choice {
            leaf egress-engineering {
              type empty;
            }
            container egress-engineering-peerset {
              tailf:cli-drop-node-name;
              container egress-engineering {
                leaf peer-set {
                  type string;
                }
              }
            }
          }
          leaf remote-as {
            type asn-type;
          }
        }
      }
      uses router-bgp-grouping;
      container af-linkstate {
        tailf:cli-drop-node-name;
        container address-family {
          container link-state {
            tailf:cli-add-mode;
            presence "true";
            uses router-bgp-af-dampening-grouping;
            container nexthop {
              leaf route-map {
                type string;
              }
              container trigger-delay {
                tailf:cli-compact-syntax;
                tailf:cli-sequence-commands {
                  tailf:cli-reset-siblings;
                }
                leaf critical {
                  type uint32;
                }
                leaf non-critical {
                  type uint32;
                }
              }
            }
          }
        }
      }
      leaf enforce-first-as {
        type boolean;
      }
      container disable-policy-batching {
        presence "true";
        container ipv4 {
          leaf prefix-list {
            type string;
          }
        }
        container ipv6 {
          leaf prefix-list {
            type string;
          }
        }
      }
      list vrf {
        key "name";
        leaf name {
          type string;
        }
        uses router-bgp-grouping {
          augment "address-family/redistribute" {
            container hmm {
              leaf route-map {
                type string;
              }
            }
          }
        }
        leaf local-as {
          type asn-type;
        }
      }
      container event-history {

        grouping eh-size-leaf {
          leaf size {
            type union {
              type uint32;
              type enumeration {
                enum "large";
                enum "medium";
                enum "small";
              }
            }
          }
        }
        container events {
          uses eh-size-leaf;
        }
        container errors {
          uses eh-size-leaf;
        }
        container cli {
          uses eh-size-leaf;
        }
        container socket {
          uses eh-size-leaf;
        }
        container detail {
          uses eh-size-leaf;
        }
        container objstore {
          uses eh-size-leaf;
        }
        container periodic {
          uses eh-size-leaf;
        }
      }
    }
    list ospf {
      key "id";
      leaf id {
        tailf:cli-suppress-range;
        type ospf-id-type;
      }
      leaf isolate {
        type empty;
      }
      container ip {
        container ospf {
          list event-history {
            tailf:cli-suppress-mode;
            tailf:cli-delete-when-empty;
            key "event";
            leaf event {
              type enumeration {
                enum "adjacency";
                enum "cli";
                enum "event";
                enum "flooding";
                enum "ha";
                enum "hello";
                enum "ldp";
                enum "lsa";
                enum "objstore";
                enum "redistribution";
                enum "rib";
                enum "segrt";
                enum "spf";
                enum "spf-trigger";
                enum "te";
              }
            }
            leaf size {
              type union {
                type uint16;
                type enumeration {
                  enum "disabled";
                  enum "large";
                  enum "medium";
                }
              }
            }
          }
        }
      }
      list network {
        tailf:cli-suppress-mode;
        tailf:cli-delete-when-empty;
        key "ip";
        leaf ip {
          type tailf:ipv4-address-and-prefix-length;
        }
        leaf area {
          type ospf-area-type;
        }
      }
      uses ospf-grouping;
      list vrf {
        key "name";
        leaf name {
          type string;
        }
        container capability {
          tailf:cli-compact-syntax;
          tailf:cli-sequence-commands {
            tailf:cli-reset-siblings;
          }
          leaf vrf-lite {
            type empty;
          }
          leaf evpn {
            type empty;
          }
        }
        uses ospf-grouping;
      }
    }
    list ospfv3 {
      key "tag";
      leaf tag {
        type string;
      }
      leaf isolate {
        type empty;
      }
      uses ospf-ospfv3-common-grouping;
      uses ospfv3-address-family-grouping;
      list vrf {
        key "name";
        leaf name {
          type string;
        }
        uses ospf-ospfv3-common-grouping;
        uses ospfv3-address-family-grouping;
      }
    }
    list isis {
      key "id";
      leaf id {
        type string;
      }
      container mpls {
        container ldp {
          leaf autoconfig {
            type enumeration {
              enum "level-1";
              enum "level-1-2";
              enum "level-2";
            }
          }
          leaf sync {
            type empty;
          }
        }
      }
      uses isis-common-grouping;
      list vrf {
        key "name";
        leaf name {
          type string;
        }
        uses isis-common-grouping;
      }
    }
    list eigrp {
      key "id";
      leaf id {
        type string;
      }
      uses eigrp-common-grouping;
      uses eigrp-common-af-grouping;
      list vrf {
        key "name";
        leaf name {
          type string;
        }
        uses eigrp-common-grouping;
        uses eigrp-common-af-grouping;
      }
    }
    list rip {
      key "id";
      leaf id {
        type string;
      }
      leaf flush-routes {
        type empty;
      }
      container metric {
        leaf direct {
          type uint8;
        }
      }
      uses rip-common-af-grouping;
      list vrf {
        key "name";
        leaf name {
          type string;
        }
        uses rip-common-af-grouping;
      }
    }
  }
  container poap {
    leaf transit {
      type empty;
    }
  }
  container logging {
    container level {
      list facilities {
        tailf:cli-suppress-mode;
        tailf:cli-drop-node-name;
        tailf:cli-delete-when-empty;
        key "facility sub-function";
        leaf facility {
          type string;
        }
        leaf sub-function {
          type string;
        }
        leaf level {
          tailf:cli-drop-node-name;
          type loglevel-type;
        }
      }
      container ethpm {
        leaf level {
          tailf:cli-drop-node-name;
          type loglevel-type;
        }
        leaf link-up {
          type enumeration {
            enum "notif";
            enum "error";
          }
        }
        leaf link-down {
          type enumeration {
            enum "notif";
            enum "error";
          }
        }
      }
    }
    leaf rfc-strict {
      type enumeration {
        enum "5424";
      }
    }
    list server {
      tailf:cli-suppress-mode;
      tailf:cli-delete-when-empty;
      tailf:cli-compact-syntax;
      tailf:cli-sequence-commands;
      key "host";
      leaf host {
        type string;
      }
      leaf level {
        tailf:cli-drop-node-name;
        tailf:cli-optional-in-sequence;
        type loglevel-type;
      }
      leaf port {
        tailf:cli-optional-in-sequence;
        type uint16;
      }
      leaf secure {
        tailf:cli-optional-in-sequence;
        type empty;
      }
      container trustpoint {
        tailf:cli-optional-in-sequence;
        tailf:cli-flatten-container;
        leaf client-identity {
          type string;
        }
      }
      leaf use-vrf {
        tailf:cli-optional-in-sequence;
        type vrf-member-type;
      }
      leaf facility {
        type enumeration {
          enum "auth";
          enum "authpriv";
          enum "cron";
          enum "daemon";
          enum "ftp";
          enum "kernel";
          enum "local0";
          enum "local1";
          enum "local2";
          enum "local3";
          enum "local4";
          enum "local5";
          enum "local6";
          enum "local7";
          enum "lpr";
          enum "mail";
          enum "news";
          enum "syslog";
          enum "user";
          enum "uucp";
          enum "kern";
        }
      }
    }
    leaf source-interface {
      type string;
    }
    container explicit-source-interface {
      tailf:cli-drop-node-name;
      container source-interface {
        tailf:cli-sequence-commands;
        tailf:cli-compact-syntax;
        leaf interface-type {
          tailf:cli-drop-node-name;
          type enumeration {
            enum "ethernet";
            enum "loopback";
            enum "mgmt";
            enum "port-channel";
            enum "vlan";
          }
        }
        leaf interface-id {
          tailf:cli-drop-node-name;
          type string;
        }
      }
    }
    leaf timestamp {
      type enumeration {
        enum "microseconds";
        enum "milliseconds";
        enum "seconds";
      }
    }
    leaf monitor {
      type loglevel-type;
    }
    leaf module {
      type loglevel-type;
    }
    leaf console {
      type loglevel-type;
    }
    container logfile {
      tailf:cli-compact-syntax;
      tailf:cli-sequence-commands;
      choice enable-or-disable-logfile-choice {
        case enable-logfile {
          leaf name {
            tailf:cli-drop-node-name;
            type string;
          }
          leaf level {
            tailf:cli-drop-node-name;
            type loglevel-type;
          }
          leaf size {
            type uint32;
          }
        }
        case disable-logfile {
          leaf disable {
            type empty;
          }
        }
      }
    }
    container event {
      container link-status {
        leaf default {
          type boolean;
        }
        leaf enable {
          type boolean;
        }
      }
      container trunk-status {
        leaf default {
          type boolean;
        }
        leaf enable {
          type boolean;
        }
      }
    }
    container origin-id {
      choice origin-choice {
        leaf hostname {
          type empty;
        }
        leaf ip {
          type string;
        }
        leaf string {
          type string;
        }
      }
    }
    container ip {
      container access-list {
        container include {
          leaf sgt {
            type empty;
          }
        }
        container cache {
          leaf interval {
            type uint32;
          }
          leaf entries {
            type uint32;
          }
          leaf threshold {
            type uint32;
          }
        }
      }
    }
    leaf rate-limit {
      type boolean;
    }
    container history {
      leaf size {
        type uint16;
      }
      leaf level {
        tailf:cli-drop-node-name;
        type uint8;
      }
    }
  }
  container scheduler {
    list job {
      key "name";
      leaf name {
        tailf:cli-expose-key-name;
        type string;
      }
      leaf commands {
        tailf:cli-drop-node-name;
        tailf:cli-multi-value;
        type string;
      }
    }
    list schedule {
      key "name";
      leaf name {
        tailf:cli-expose-key-name;
        type string;
      }
      container job {
        leaf name {
          type string;
        }
      }
      container time {
        choice sched-choice {
          leaf daily {
            type string;
          }
          leaf weekly {
            type string;
          }
          leaf monthly {
            type string;
          }
        }
      }
    }
  }
  container role {
    list name {
      key "name";
      leaf name {
        type user-role-type;
      }
      leaf description {
        tailf:cli-multi-value;
        type string;
      }
      list rule {
        tailf:cli-suppress-mode;
        tailf:cli-delete-when-empty;
        key "id";
        leaf id {
          type uint16;
        }
        choice permit-or-deny {
          container deny {
            uses role-rule-type-choice;
          }
          container permit {
            uses role-rule-type-choice;
          }
        }
      }
      container vlan {
        container policy {
          container deny {
            tailf:cli-add-mode;
            presence "true";
            container permit {
              leaf-list vlan {
                tailf:cli-range-list-syntax;
                type uint16;
              }
            }
          }
        }
      }
      container interface {
        container policy {
          container deny {
            tailf:cli-add-mode;
            presence "true";
            container permit {
              list interface {
                tailf:cli-suppress-mode;
                tailf:cli-delete-when-empty;
                key "name";
                leaf name {
                  type string;
                }
              }
            }
          }
        }
      }
      container vrf {
        container policy {
          container deny {
            tailf:cli-add-mode;
            presence "true";
            container permit {
              list vrf {
                tailf:cli-suppress-mode;
                tailf:cli-delete-when-empty;
                key "name";
                leaf name {
                  type string;
                }
              }
            }
          }
        }
      }
    }
  }

  grouping role-rule-type-choice {
    choice rule-type {
      leaf command {
        tailf:cli-multi-value;
        type string;
      }
      container read {
        presence "true";
        leaf feature {
          type string;
        }
        leaf feature-group {
          type string;
        }
        leaf oid {
          type string;
        }
      }
      container read-write {
        presence "true";
        leaf feature {
          type string;
        }
        leaf feature-group {
          type string;
        }
        leaf oid {
          type string;
        }
      }
    }
  }

  container svs-domain {
    tailf:cli-add-mode;
    container domain {
      leaf id {
        type uint16;
      }
    }
    container control {
      leaf vlan {
        type uint16;
      }
    }
    container packet {
      leaf vlan {
        type uint16;
      }
    }
    container svs {
      container mode {
        container L3 {
          leaf interface {
            type string;
          }
        }
        container L2 {
          presence "true";
        }
      }
    }
    leaf switch-guid {
      type string;
    }
  }
  container svs {
    list connection {
      key "name";
      leaf name {
        type string;
      }
      leaf protocol {
        type enumeration {
          enum "vmware-vim";
        }
      }
      container remote {
        container ip {
          tailf:cli-compact-syntax;
          leaf address {
            type inet:ipv4-address;
          }
          leaf port {
            type uint16;
          }
        }
      }
      container vmware {
        container dvs {
          tailf:cli-compact-syntax;
          leaf uuid {
            type string;
          }
          leaf datacenter-name {
            type string;
          }
        }
      }
      leaf max-ports {
        type uint16;
      }
      leaf connect {
        type empty;
      }
    }
  }
  container vservice {
    container global {
      list type {
        key "id";
        leaf id {
          type enumeration {
            enum "vsg";
          }
        }
        container tcp {
          container state-checks {
            leaf invalid-ack {
              type boolean;
            }
            leaf seq-past-window {
              type boolean;
            }
            leaf window-variation {
              type boolean;
            }
          }
        }
        container bypass {
          leaf asa-traffic {
            type boolean;
          }
        }
        leaf l3-frag {
          type boolean;
        }
      }
    }
  }
  container vnm-policy-agent {
    tailf:cli-add-mode;
    leaf registration-ip {
      type inet:ipv4-address;
    }
    leaf shared-secret {
      type string;
    }
    leaf policy-agent-image {
      type string;
    }
    leaf log-level {
      type string;
    }
  }
  container spanning-tree {
    leaf mode {
      type enumeration {
        enum "mst";
        enum "rapid-pvst";
      }
    }
    container mst {
      leaf forward-time {
        type uint8;
      }
      leaf hello-time {
        type uint8;
      }
      leaf max-age {
        type uint8;
      }
      leaf max-hops {
        type uint8;
      }
      container simulate {
        tailf:cli-compact-syntax;
        container pvst {
          leaf global {
            type boolean;
          }
        }
      }
      container configuration {
        tailf:cli-add-mode;
        tailf:cli-delete-when-empty;
        leaf name {
          type string;
        }
        leaf revision {
          type uint16;
        }
        container instance {
          tailf:cli-compact-syntax;
          leaf id {
            tailf:cli-drop-node-name;
            type uint16;
          }
          leaf-list vlan {
            tailf:cli-range-list-syntax;
            type uint16;
          }
        }
      }
      list mst-instance {
        tailf:cli-drop-node-name;
        tailf:cli-suppress-mode;
        tailf:cli-delete-when-empty;
        tailf:cli-range-list-syntax;
        key "id";
        leaf id {
          type uint16;
        }
        leaf priority {
          type uint16;
        }
      }
    }
    container vlan {
      list no-list {
        tailf:cli-suppress-mode;
        tailf:cli-delete-when-empty;
        tailf:cli-range-list-syntax;
        key "id";
        leaf id {
          type uint16;
        }
      }
      list vlan-list {
        tailf:cli-drop-node-name;
        tailf:cli-suppress-mode;
        tailf:cli-delete-when-empty;
        tailf:cli-range-list-syntax;
        key "id";
        leaf id {
          type uint16;
        }
        leaf forward-time {
          type uint8;
        }
        leaf hello-time {
          type uint8;
        }
        leaf max-age {
          type uint8;
        }
        leaf priority {
          type uint16;
        }
      }
    }
    container port {
      container type {
        container edge {
          container bpduguard {
            leaf default {
              type empty;
            }
          }
          container bpdufilter {
            leaf default {
              type empty;
            }
          }
          leaf default {
            type empty;
          }
        }
        container network {
          leaf default {
            type empty;
          }
        }
      }
    }
    container pathcost {
      leaf method {
        type enumeration {
          enum "long";
          enum "short";
        }
      }
    }
    container loopguard {
      leaf default {
        type empty;
      }
    }
    leaf lc-issu {
      type enumeration {
        enum "auto";
        enum "disruptive";
        enum "non-disruptive";
      }
    }
    container bridge {
      leaf assurance {
        type boolean;
      }
    }
    container pseudo-information {
      tailf:cli-add-mode;
      list vlan {
        tailf:cli-suppress-mode;
        tailf:cli-delete-when-empty;
        tailf:cli-range-list-syntax;
        key "vlan-ids";
        leaf vlan-ids {
          type uint16;
        }
        container designated {
          leaf priority {
            type uint16;
          }
        }
        container root {
          leaf priority {
            type uint16;
          }
        }
      }
    }
  }
  container event {
    container manager {
      list applet {
        key "name";
        leaf name {
          type string;
        }
        leaf class {
          tailf:cli-hide-in-submode;
          type string;
        }
        leaf description {
          tailf:cli-multi-value;
          type string;
        }
        container event {
          choice event-type-choice {
            container syslog {
              leaf pattern {
                type string;
              }
              list tag {
                tailf:cli-suppress-mode;
                tailf:cli-delete-when-empty;
                tailf:cli-compact-syntax;
                key "name";
                leaf name {
                  type string;
                }
                leaf pattern {
                  type string;
                }
              }
            }
            container snmp {
              tailf:cli-sequence-commands {
                tailf:cli-reset-siblings;
              }
              tailf:cli-compact-syntax;
              leaf oid {
                type string;
              }
              leaf get-type {
                type enumeration {
                  enum "exact";
                  enum "next";
                }
              }
              leaf entry-op {
                type comparison-type;
              }
              leaf entry-val {
                type uint64;
              }
              leaf exit-op {
                tailf:cli-optional-in-sequence;
                type comparison-type;
              }
              leaf exit-val {
                type uint64;
              }
              leaf poll-interval {
                type uint32;
              }
            }
            container track {
              tailf:cli-sequence-commands;
              tailf:cli-compact-syntax;
              leaf tag {
                tailf:cli-optional-in-sequence;
                type string;
              }
              leaf track-objects {
                tailf:cli-drop-node-name;
                type uint16;
              }
              leaf state {
                type enumeration {
                  enum "any";
                  enum "down";
                  enum "up";
                }
              }
            }
            container module {
              tailf:cli-sequence-commands;
              tailf:cli-compact-syntax;
              leaf tag {
                tailf:cli-optional-in-sequence;
                type string;
              }
              leaf status {
                type enumeration {
                  enum "any";
                  enum "offline";
                  enum "online";
                }
              }
              leaf module {
                type union {
                  type uint8;
                  type enumeration {
                    enum "all";
                  }
                }
              }
            }
            container timer {
              choice timer-choice {
                container absolute {
                  leaf time {
                    type string;
                  }
                }
                container countdown {
                  leaf time {
                    type string;
                  }
                }
                container cron {
                  leaf cron-entry {
                    type string;
                  }
                }
                container watchdog {
                  leaf time {
                    type string;
                  }
                }
              }
            }
          }
        }
        list action {
          tailf:cli-suppress-mode;
          key "label";
          leaf label {
            type string;
          }
          leaf actions {
            tailf:cli-drop-node-name;
            tailf:cli-multi-value;
            type string;
          }
        }
        leaf maxrun {
          type uint32;
        }
        container tag {
          tailf:cli-compact-syntax;
          tailf:cli-sequence-commands {
            tailf:cli-reset-siblings;
          }
          leaf tag-name {
            tailf:cli-drop-node-name;
            type string;
          }
          leaf combined-2 {
            tailf:cli-drop-node-name;
            type enumeration {
              enum "and";
              enum "andnot";
              enum "or";
            }
          }
          leaf tag-name-2 {
            tailf:cli-drop-node-name;
            type string;
          }
          leaf combined-3 {
            tailf:cli-drop-node-name;
            tailf:cli-optional-in-sequence;
            type enumeration {
              enum "and";
              enum "andnot";
              enum "or";
            }
          }
          leaf tag-name-3 {
            tailf:cli-drop-node-name;
            type string;
          }
          leaf combined-4 {
            tailf:cli-drop-node-name;
            tailf:cli-optional-in-sequence;
            type enumeration {
              enum "and";
              enum "andnot";
              enum "or";
            }
          }
          leaf tag-name-4 {
            tailf:cli-drop-node-name;
            type string;
          }
          leaf happens {
            type uint32;
          }
          leaf in {
            type uint32;
          }
        }
      }
      container scheduler {
        container applet {
          container thread {
            list class {
              tailf:cli-suppress-mode;
              tailf:cli-delete-when-empty;
              tailf:cli-compact-syntax;
              key "value";
              leaf value {
                type string;
              }
              leaf number {
                type uint16;
              }
            }
          }
        }
      }
    }
  }
  container monitor {
    list session {
      key "id";
      leaf id {
        type uint8;
      }
      leaf type {
        tailf:cli-hide-in-submode;
        type enumeration {
          enum "erspan-destination";
          enum "erspan-source";
          enum "local";
          enum "acl-capture";
        }
      }
      leaf direction {
        tailf:cli-hide-in-submode;
        tailf:cli-drop-node-name;
        type enumeration {
          enum "rx";
          enum "tx";
        }
      }
      leaf description {
        tailf:cli-multi-value;
        type string;
      }
      leaf header-type {
        type uint8;
      }
      leaf mtu {
        type uint16;
      }
      leaf rate-limit {
        type union {
          type uint8;
          type enumeration {
            enum "auto";
          }
        }
      }
      leaf sampling {
        type uint16;
      }
      container source {
        list interface {
          tailf:cli-suppress-mode;
          tailf:cli-delete-when-empty;
          key "name";
          leaf name {
            type string;
          }
          leaf direction {
            tailf:cli-drop-node-name;
            type enumeration {
              enum "both";
              enum "rx";
              enum "tx";
            }
          }
        }
        list vlan {
          tailf:cli-suppress-mode;
          tailf:cli-delete-when-empty;
          tailf:cli-range-list-syntax;
          key "id";
          leaf id {
            type uint16;
          }
          leaf direction {
            tailf:cli-drop-node-name;
            type enumeration {
              enum "both";
              enum "rx";
              enum "tx";
            }
          }
        }
        leaf ip {
          type inet:ipv4-address;
        }
        container exception {
          leaf fabricpath {
            type empty;
          }
          leaf layer3 {
            type empty;
          }
          leaf other {
            type empty;
          }
        }
      }
      container destination {
        list interface {
          tailf:cli-suppress-mode;
          tailf:cli-delete-when-empty;
          key "name";
          leaf name {
            type string;
          }
          leaf primary {
            type empty;
          }
        }
        leaf ip {
          type inet:ipv4-address;
        }
      }
      leaf shut {
        type boolean;
      }
      container filter {
        container access-group {
          tailf:cli-compact-syntax;
          tailf:cli-sequence-commands {
            tailf:cli-reset-siblings;
          }
          leaf name {
            tailf:cli-drop-node-name;
            type string;
          }
          leaf allow-sharing {
            type empty;
          }
        }
        leaf bpdu {
          type boolean;
        }
        leaf cos {
          type uint8;
        }
        container dest-mac {
          tailf:cli-compact-syntax;
          tailf:cli-sequence-commands;
          leaf address {
            tailf:cli-drop-node-name;
            type string;
          }
          leaf mask {
            tailf:cli-drop-node-name;
            type string;
          }
        }
        container src-mac {
          tailf:cli-compact-syntax;
          tailf:cli-sequence-commands;
          leaf address {
            tailf:cli-drop-node-name;
            type string;
          }
          leaf mask {
            tailf:cli-drop-node-name;
            type string;
          }
        }
        leaf eth-type {
          type string;
        }
        leaf-list vlan {
          tailf:cli-range-list-syntax;
          type uint16;
        }
        container frame-type {

          grouping ip-type-grouping {
            leaf l4-protocol {
              type union {
                type uint8;
                type enumeration {
                  enum "egp";
                  enum "gre";
                  enum "icmp";
                  enum "igmp";
                  enum "igp";
                  enum "ospf";
                  enum "rsvp";
                  enum "tcp";
                  enum "udp";
                  enum "ipv6-icmp";
                  enum "ipv6-route";
                  enum "no-nxt";
                  enum "shim6";
                }
              }
            }
            leaf tos {
              type uint8;
            }
          }
          choice type-choice {
            container arp {
              presence "true";
              leaf arp-rarp {
                type enumeration {
                  enum "arp";
                  enum "rarp";
                }
              }
              leaf sender-ip {
                type tailf:ipv4-address-and-prefix-length;
              }
              leaf target-ip {
                type tailf:ipv4-address-and-prefix-length;
              }
            }
            container eth {
              presence "true";
            }
            container fcoe {
              presence "true";
            }
            container ipv4 {
              presence "true";
              leaf dest-ip {
                type tailf:ipv4-address-and-prefix-length;
              }
              leaf src-ip {
                type tailf:ipv4-address-and-prefix-length;
              }
              uses ip-type-grouping;
            }
            container ipv6 {
              presence "true";
              leaf dest-ip {
                type tailf:ipv6-address-and-prefix-length;
              }
              leaf src-ip {
                type tailf:ipv6-address-and-prefix-length;
              }
              uses ip-type-grouping;
            }
          }
        }
      }
      leaf erspan-id {
        type uint16;
      }
      leaf vrf {
        type string;
      }
      container ip {
        leaf dscp {
          type uint8;
        }
        leaf ttl {
          type uint8;
        }
      }
      leaf marker-packet {
        type uint16;
      }
    }
    container erspan {
      container origin {
        tailf:cli-compact-syntax;
        tailf:cli-sequence-commands {
          tailf:cli-reset-siblings;
        }
        leaf ip-address {
          type union {
            type inet:ipv4-address;
            type inet:ipv6-address;
          }
        }
        leaf global {
          type empty;
        }
      }
    }
  }
  container itd {
    list device-group {
      key "group-name";
      leaf group-name {
        type word32;
      }
      uses itd-probe-grouping;
      container node {
        list ip {
          key "address";
          leaf address {
            type inet:ipv4-address;
          }
          leaf mode {
            type enumeration {
              enum "hot-standby";
            }
          }
          list standby {
            key "address";
            leaf address {
              type inet:ipv4-address;
            }
          }
          leaf weight {
            type uint16;
          }
          uses itd-probe-grouping;
        }
      }
    }
    list service {
      tailf:cli-drop-node-name;
      key "name";
      leaf name {
        type word32;
      }
      leaf access-list {
        type word50;
      }
      leaf device-group {
        type word32;
      }
      container exclude {
        leaf access-list {
          type word50;
        }
      }
      container failaction {
        leaf node {
          type enumeration {
            enum "reassign";
            enum "least-bucket";
            enum "per-bucket";
          }
        }
      }
      container ingress {
        list interface {
          tailf:cli-suppress-mode;
          key "name";
          leaf name {
            type string;
          }
        }
      }
      container load-balance {
        tailf:cli-compact-syntax;
        tailf:cli-sequence-commands {
          tailf:cli-reset-siblings;
        }
        container method {
          tailf:cli-flatten-container;
          tailf:cli-compact-syntax;
          tailf:cli-sequence-commands;
          tailf:cli-optional-in-sequence;
          leaf method {
            tailf:cli-drop-node-name;
            type enumeration {
              enum "dst";
              enum "src";
            }
          }
          choice type {
            case ip {
              leaf ip {
                type empty;
              }
            }
            case ip-l4port {
              leaf ip-l4port {
                type empty;
              }
              leaf protocol {
                tailf:cli-drop-node-name;
                type enumeration {
                  enum "tcp";
                  enum "udp";
                }
              }
              leaf range {
                type uint16;
              }
              leaf last {
                tailf:cli-drop-node-name;
                type uint16;
              }
            }
          }
        }
        leaf buckets {
          tailf:cli-optional-in-sequence;
          type uint16;
        }
        leaf mask-position {
          type uint8;
        }
      }
      container peer {
        container local {
          leaf service {
            type string;
          }
        }
        container vdc {
          tailf:cli-compact-syntax;
          tailf:cli-sequence-commands {
            tailf:cli-reset-siblings;
          }
          leaf name {
            tailf:cli-drop-node-name;
            type string;
          }
          leaf service {
            type string;
          }
        }
      }
      container virtual {
        tailf:cli-compact-syntax;
        list ip {
          tailf:cli-suppress-mode;
          tailf:cli-delete-when-empty;
          tailf:cli-compact-syntax;
          tailf:cli-sequence-commands;
          key "address";
          leaf address {
            type inet:ipv4-address;
          }
          leaf mask {
            tailf:cli-drop-node-name;
            type inet:ipv4-address;
          }
          choice proto {
            leaf tcp {
              tailf:cli-optional-in-sequence;
              type union {
                type uint16;
                type enumeration {
                  enum "any";
                }
              }
            }
            leaf udp {
              tailf:cli-optional-in-sequence;
              type union {
                type uint16;
                type enumeration {
                  enum "any";
                }
              }
            }
          }
          leaf advertise {
            type enumeration {
              enum "enable";
              enum "disable";
            }
          }
          leaf active {
            type empty;
          }
        }
      }
      leaf vrf {
        type word32;
      }
      leaf shut {
        type boolean;
      }
    }
  }

  grouping itd-probe-grouping {
    container probe {
      tailf:cli-compact-syntax;
      tailf:cli-sequence-commands {
        tailf:cli-reset-siblings;
      }
      leaf protocol {
        tailf:cli-drop-node-name;
        type enumeration {
          enum "dns";
          enum "icmp";
          enum "tcp";
          enum "udp";
        }
      }
      leaf host {
        type string;
      }
      leaf port {
        type uint16;
      }
      leaf frequency {
        tailf:cli-optional-in-sequence;
        type uint32;
      }
      leaf timeout {
        tailf:cli-optional-in-sequence;
        type uint32;
      }
      leaf retry-down-count {
        tailf:cli-optional-in-sequence;
        type uint8;
      }
      leaf retry-up-count {
        tailf:cli-optional-in-sequence;
        type uint8;
      }
    }
  }

  container nsc-policy-agent {
    tailf:cli-add-mode;
    leaf registration-ip {
      type inet:ipv4-address;
    }
    leaf shared-secret {
      type string;
    }
    leaf log-level {
      type string;
    }
  }
  container network {
    container segment {
      container manager {
        container switch {
          tailf:cli-add-mode;
          container dvs {
            leaf name {
              type string;
            }
          }
        }
      }
      list policy {
        key "name";
        leaf name {
          type string;
        }
        leaf description {
          tailf:cli-multi-value;
          type string;
        }
        leaf type {
          type string;
        }
        container import {
          leaf port-profile {
            type string;
          }
        }
      }
    }
  }
  container nsm {
    container ip {
      container pool {
        list template {
          key "name";
          leaf name {
            type string;
          }
          leaf description {
            tailf:cli-multi-value;
            type string;
          }
          container ip {
            container address {
              tailf:cli-sequence-commands;
              tailf:cli-compact-syntax;
              leaf start {
                tailf:cli-drop-node-name;
                type inet:ipv4-address;
              }
              leaf end {
                tailf:cli-drop-node-name;
                type inet:ipv4-address;
              }
            }
          }
          container network {
            tailf:cli-compact-syntax;
            tailf:cli-sequence-commands;
            leaf address {
              tailf:cli-drop-node-name;
              type inet:ipv4-address;
            }
            leaf mask {
              tailf:cli-drop-node-name;
              type inet:ipv4-address;
            }
          }
        }
      }
    }
    container logical {
      list network {
        key "name";
        leaf name {
          type string;
        }
        leaf description {
          tailf:cli-multi-value;
          type string;
        }
      }
    }
    container network {
      container segment {
        list pool {
          key "name";
          leaf name {
            type string;
          }
          leaf description {
            tailf:cli-multi-value;
            type string;
          }
          leaf uuid {
            type string;
          }
          container member-of {
            container logical {
              leaf network {
                type string;
              }
            }
          }
        }
        list segment-list {
          tailf:cli-drop-node-name;
          key "name";
          leaf name {
            type string;
          }
          leaf description {
            tailf:cli-multi-value;
            type string;
          }
          leaf uuid {
            type string;
          }
          container member-of {
            container network {
              container segment {
                leaf pool {
                  type string;
                }
              }
            }
          }
          container switchport {
            leaf mode {
              type enumeration {
                enum "access";
                enum "trunk";
              }
            }
            container access {
              leaf vlan {
                type uint16;
              }
            }
            container trunk {
              container native {
                leaf-list vlan {
                  tailf:cli-range-list-syntax;
                  type uint16;
                }
              }
              container allowed {
                leaf-list vlan {
                  tailf:cli-range-list-syntax;
                  type uint16;
                }
              }
            }
          }
          container ip {
            container pool {
              container import {
                tailf:cli-compact-syntax;
                leaf template {
                  type string;
                }
                leaf uuid {
                  type string;
                }
              }
            }
          }
          container publish {
            container network {
              container segment {
                presence "true";
                leaf name {
                  tailf:cli-drop-node-name;
                  type string;
                }
              }
            }
          }
        }
      }
      list vethernet {
        key "name";
        leaf name {
          type string;
        }
        container import {
          container port-profile {
            tailf:cli-compact-syntax;
            tailf:cli-sequence-commands;
            leaf name {
              tailf:cli-drop-node-name;
              type string;
            }
            leaf uuid {
              type string;
            }
          }
        }
        container allow {
          container network {
            tailf:cli-compact-syntax;
            leaf segment {
              type string;
            }
            leaf uuid {
              type string;
            }
          }
        }
        leaf state {
          type enumeration {
            enum "enabled";
            enum "disabled";
          }
        }
        container port {
          list uuid {
            tailf:cli-suppress-mode;
            tailf:cli-delete-when-empty;
            tailf:cli-compact-syntax;
            key "name";
            leaf name {
              type string;
            }
            leaf mac {
              type string;
            }
          }
        }
      }
    }
  }
  list track {
    key "id";
    leaf id {
      type uint16;
    }
    container interface {
      tailf:cli-hide-in-submode;
      tailf:cli-flatten-container;
      tailf:cli-compact-syntax;
      tailf:cli-sequence-commands;
      leaf name {
        tailf:cli-drop-node-name;
        type string;
      }
      leaf ip {
        tailf:cli-optional-in-sequence;
        type enumeration {
          enum "routing";
        }
      }
      leaf line-protocol {
        type empty;
      }
    }
    container ip {
      tailf:cli-hide-in-submode;
      tailf:cli-flatten-container;
      tailf:cli-compact-syntax;
      tailf:cli-sequence-commands;
      choice route-or-sla {
        leaf route {
          type ip-mask;
        }
        leaf sla {
          type uint32;
        }
      }
      leaf reachability {
        type empty;
      }
      leaf hmm {
        type empty;
      }
    }
    container ipv6 {
      tailf:cli-hide-in-submode;
      tailf:cli-flatten-container;
      tailf:cli-compact-syntax;
      tailf:cli-sequence-commands;
      leaf route {
        type tailf:ipv6-address-and-prefix-length;
      }
      leaf reachability {
        type empty;
      }
      leaf hmm {
        type empty;
      }
    }
    container list {
      tailf:cli-hide-in-submode;
      tailf:cli-flatten-container;
      tailf:cli-compact-syntax;
      tailf:cli-sequence-commands;
      choice bool-or-threshold {
        leaf boolean {
          type enumeration {
            enum "and";
            enum "or";
          }
        }
        leaf threshold {
          type enumeration {
            enum "percentage";
            enum "weight";
          }
        }
      }
    }
    container delay {
      tailf:cli-compact-syntax;
      leaf up {
        type uint8;
      }
      leaf down {
        type uint8;
      }
    }
    container vrf {
      leaf member {
        type vrf-member-type;
      }
    }
    list object {
      tailf:cli-suppress-mode;
      key "id";
      leaf id {
        type uint16;
      }
      leaf not {
        type empty;
      }
    }
  }
  container ngoam {
    leaf authentication-key {
      type string;
    }
    container install {
      leaf acl {
        type empty;
      }
    }
    list profile {
      key "id";
      leaf id {
        type uint16;
      }
      leaf description {
        tailf:cli-multi-value;
        type string;
      }
      container dot1q {
        tailf:cli-compact-syntax;
        tailf:cli-sequence-commands {
          tailf:cli-reset-siblings;
        }
        leaf value {
          tailf:cli-drop-node-name;
          type uint16;
        }
        leaf interface {
          tailf:cli-drop-node-name;
          type string;
        }
      }
      container flow {
        container forward {
          tailf:cli-add-mode;
          presence "true";
          leaf dot1q {
            type uint16;
          }
          choice ipv4-or-ipv6 {
            container ip {
              leaf destination {
                type inet:ipv4-address;
              }
              leaf source {
                type inet:ipv4-address;
              }
            }
            container ipv6 {
              leaf destination {
                type inet:ipv6-address;
              }
              leaf source {
                type inet:ipv6-address;
              }
            }
          }
          container mac-address {
            leaf destination {
              type string;
            }
            leaf source {
              type string;
            }
          }
          leaf packet {
            type string;
          }
          container port {
            leaf destination {
              type uint16;
            }
            leaf source {
              type uint16;
            }
          }
          leaf protocol {
            type uint8;
          }
        }
      }
      leaf hop {
        type uint8;
      }
      leaf interface {
        type string;
      }
      leaf oam-channel {
        type uint8;
      }
      container payload {
        leaf pad {
          type string;
        }
      }
      leaf-list sport {
        tailf:cli-range-list-syntax;
        type uint16;
      }
    }
    list connect-check {
      key "id";
      leaf id {
        type uint16;
      }
      leaf interval {
        type uint8;
      }
      leaf packet-size {
        type uint16;
      }
      leaf profile {
        type uint16;
      }
      leaf timeout {
        type uint8;
      }
      leaf verify-host {
        type empty;
      }
      leaf vni {
        type uint32;
      }
      leaf vrf {
        type vrf-member-type;
      }
    }
    container loop-detection {
      tailf:cli-add-mode;
      presence "true";
      leaf periodic-probe-interval {
        type uint16;
      }
      leaf port-recovery-interval {
        type uint16;
      }
      container disable {
        tailf:cli-compact-syntax;
        tailf:cli-sequence-commands {
          tailf:cli-reset-siblings;
        }
        leaf-list vlan {
          tailf:cli-range-list-syntax;
          type uint16;
        }
        leaf port {
          type string;
        }
      }
    }
  }
  container terminal {
    leaf log-all {
      type empty;
    }
  }
  container telnet {
    container server {
      leaf enable {
        type boolean;
      }
    }
    leaf login-attempts {
      type uint8;
    }
  }
  container boot {
    container kickstart {
      tailf:cli-compact-syntax;
      tailf:cli-sequence-commands {
        tailf:cli-reset-siblings;
      }
      uses boot-image-grouping;
    }
    container system {
      tailf:cli-compact-syntax;
      tailf:cli-sequence-commands {
        tailf:cli-reset-siblings;
      }
      uses boot-image-grouping;
    }
    container nxos {
      tailf:cli-compact-syntax;
      tailf:cli-sequence-commands {
        tailf:cli-reset-siblings;
      }
      uses boot-image-grouping;
    }
    container poap {
      leaf enable {
        type empty;
      }
    }
  }

  grouping boot-image-grouping {
    leaf image {
      tailf:cli-drop-node-name;
      type string;
    }
    leaf module {
      tailf:cli-drop-node-name;
      type enumeration {
        enum "sup-1";
        enum "sup-2";
      }
    }
  }

  container hw-module {
    container logging {
      leaf onboard {
        type boolean;
      }
      container onboard-per-module {
        tailf:cli-drop-node-name;
        container onboard {
          list module {
            tailf:cli-suppress-mode;
            tailf:cli-delete-when-empty;
            key "id";
            leaf id {
              type uint8;
            }
            leaf counter-stats {
              type boolean;
            }
            leaf cpuhog {
              type boolean;
            }
            leaf environmental-history {
              type boolean;
            }
            leaf error-stats {
              type boolean;
            }
            leaf interrupt-stats {
              type boolean;
            }
            leaf obfl-log {
              type boolean;
            }
            leaf memory-info {
              type boolean;
            }
          }
        }
      }
    }
  }
  container intersight {
    leaf connection {
      type string;
    }
    leaf inventory {
      type boolean;
    }
    container proxy {
      tailf:cli-compact-syntax;
      tailf:cli-sequence-commands {
        tailf:cli-reset-siblings;
      }
      leaf host {
        tailf:cli-drop-node-name;
        type string;
      }
      leaf port {
        type uint16;
      }
    }
    leaf source-interface {
      type string;
    }
    leaf trustpoint {
      type string;
    }
    leaf use-vrf {
      type string;
    }
  }
  container switch-profile {
    tailf:cli-add-mode;
    leaf name {
      tailf:cli-drop-node-name;
      tailf:cli-hide-in-submode;
      type string;
    }
    container sync-peers {
      leaf destination {
        type inet:ipv4-address;
      }
    }
  }
  leaf as-format {
    type enumeration {
      enum "asdot";
    }
  }
  container switching-mode {
    leaf store-forward {
      type empty;
    }
  }
  container conf_xml {
    tailf:alt-name "xml";
    container server {
      container validate {
        leaf all {
          type empty;
        }
      }
    }
  }
}
