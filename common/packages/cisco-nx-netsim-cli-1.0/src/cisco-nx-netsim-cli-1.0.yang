module cisco-nx-netsim-cli-1.0 {
  yang-version 1.1;
  namespace "http://tail-f.com/ns/ned-id/cisco-nx-netsim-cli-1.0";
  prefix cisco-nx-netsim-cli-1.0;

  import cisco-nx-netsim-cli {
    prefix family;
  }

  identity cisco-nx-netsim-cli-1.0 {
    base family:cisco-nx-netsim-cli;
  }
}
