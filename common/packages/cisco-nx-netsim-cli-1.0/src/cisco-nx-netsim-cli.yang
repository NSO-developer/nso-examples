module cisco-nx-netsim-cli {
  yang-version 1.1;
  namespace "http://tail-f.com/ns/ned-id/cisco-nx-netsim-cli";
  prefix cisco-nx-netsim-cli;

  import tailf-common {
    prefix tailf;
  }

  import tailf-ncs-ned {
    prefix ned;
  }

  identity cisco-nx-netsim-cli {
    tailf:abstract;
    base ned:cli-ned-id;
  }
}
