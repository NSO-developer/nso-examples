module netsim-ned-dell-ftos-stats {
  // Generated by yanger -t ncs
  tailf:mount-id "dell-ftos-netsim-cli-1.0:dell-ftos-netsim-cli-1.0";
  tailf:ncs-device-type "cli-ned";

  namespace "http://tail-f.com/ned/dell-ftos-stats";
  prefix ftos-stats;

  import ietf-inet-types {
    prefix inet;
  }
  import ietf-yang-types {
    prefix yang;
  }
  import tailf-common {
    prefix tailf;
  }
  import tailf-ncs {
    prefix ncs;
  }

  typedef ncs_rpc_notif_ipv4-prefix {
    type string;
  }

  typedef live_ncs_ipv4-prefix {
    type string;
  }

  typedef ipv4-prefix {
    type string;
  }

  augment "/ncs:devices/ncs:device/ncs:config" {
    container exec {
      tailf:ncs-device-type "cli-ned";
      tailf:display-when "not(../../ncs:module) or ../../ncs:module[ncs:name='netsim-ned-dell-ftos-stats']";
      tailf:alt-name "exec-stats";
    }
    // NCS drop config false container stats
  }
  augment "/ncs:devices/ncs:device/ncs:live-status" {
    container exec {
      tailf:ncs-device-type "cli-ned";
      tailf:display-when "not(../../ncs:module) or ../../ncs:module[ncs:name='netsim-ned-dell-ftos-stats'] or (../../ncs:live-status-protocol[not(ncs:capability)]) or (../../ncs:live-status-protocol/ncs:capability/ncs:module[.='netsim-ned-dell-ftos-stats'])";
      tailf:alt-name "exec-stats";
    }
    container stats {
      tailf:ncs-device-type "cli-ned";
      tailf:display-when "not(../../ncs:module) or ../../ncs:module[ncs:name='netsim-ned-dell-ftos-stats'] or (../../ncs:live-status-protocol[not(ncs:capability)]) or (../../ncs:live-status-protocol/ncs:capability/ncs:module[.='netsim-ned-dell-ftos-stats'])";
      list mac-address-table {
        key "vlan-id mac";
        leaf vlan-id {
          type uint16;
        }
        leaf mac {
          type string;
        }
        leaf type {
          type string;
        }
        leaf interface {
          type string;
        }
        leaf state {
          type string;
        }
      }
      list interface {
        key "type id";
        leaf type {
          type string;
        }
        leaf id {
          type string;
        }
        leaf state {
          type enumeration {
            enum "up";
            enum "down";
          }
        }
        leaf line-protocol {
          type string;
        }
        leaf hw-address {
          type yang:mac-address;
        }
        leaf current-address {
          type yang:mac-address;
        }
        leaf index {
          type uint64;
        }
        leaf internet-address {
          type string;
        }
        leaf mtu {
          type uint16;
        }
        leaf ip-mtu {
          type uint16;
        }
        leaf line-speed {
          type string;
        }
        leaf flowcontrol-rx {
          type enumeration {
            enum "on";
            enum "off";
          }
        }
        leaf flowcontrol-tx {
          type enumeration {
            enum "on";
            enum "off";
          }
        }
        leaf arp-type {
          type string;
        }
        leaf arp-timeout {
          type string;
        }
        leaf last-clearing-counter {
          type string;
        }
        leaf queue-strategy {
          type string;
        }
        container input {
          leaf packets {
            type uint64;
          }
          leaf bytes {
            type uint64;
          }
          leaf pkts-64-byte {
            type uint64;
          }
          leaf pkts-over-64-byte {
            type uint64;
          }
          leaf pkts-over-127-byte {
            type uint64;
          }
          leaf pkts-over-255-byte {
            type uint64;
          }
          leaf pkts-over-511-byte {
            type uint64;
          }
          leaf pkts-over-1023-byte {
            type uint64;
          }
          leaf multicasts {
            type uint64;
          }
          leaf broadcasts {
            type uint64;
          }
          leaf runts {
            type uint64;
          }
          leaf giants {
            type uint64;
          }
          leaf throttles {
            type uint64;
          }
          leaf crc {
            type uint64;
          }
          leaf overrun {
            type uint64;
          }
          leaf discarded {
            type uint64;
          }
        }
        container output {
          leaf packets {
            type uint64;
          }
          leaf bytes {
            type uint64;
          }
          leaf underruns {
            type uint64;
          }
          leaf pkts-64-byte {
            type uint64;
          }
          leaf pkts-over-64-byte {
            type uint64;
          }
          leaf pkts-over-127-byte {
            type uint64;
          }
          leaf pkts-over-255-byte {
            type uint64;
          }
          leaf pkts-over-511-byte {
            type uint64;
          }
          leaf pkts-over-1023-byte {
            type uint64;
          }
          leaf multicasts {
            type uint64;
          }
          leaf broadcasts {
            type uint64;
          }
          leaf throttles {
            type uint64;
          }
          leaf discarded {
            type uint64;
          }
          leaf unicasts {
            type uint64;
          }
          leaf collisions {
            type uint64;
          }
          leaf wreddrops {
            type uint64;
          }
        }
        container rate-info {
          container input {
            leaf mbit-p-sec {
              type string;
            }
            leaf packets-p-sec {
              type uint64;
            }
            leaf percent-line-rate {
              type string;
            }
          }
          container output {
            leaf mbit-p-sec {
              type string;
            }
            leaf packets-p-sec {
              type uint64;
            }
            leaf percent-line-rate {
              type string;
            }
          }
        }
        leaf time-since-last-status-change {
          type string;
        }
      }
      tailf:alt-name "stats-stats";
    }
  }
}
