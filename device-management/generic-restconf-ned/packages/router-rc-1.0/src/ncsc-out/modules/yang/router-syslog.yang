submodule router-syslog {
  // Generated by yanger -t ncs
  tailf:mount-id "router-gen-1.0:router-gen-1.0";

  yang-version 1.1;
  belongs-to router {
    prefix r;
  }

  import ietf-inet-types {
    prefix inet;
  }
  include router-types;
  import tailf-common {
    prefix tailf;
  }
  import tailf-ncs {
    prefix ncs;
  }

  description
    "The 'syslog' component provides support for configuring logging to
     remote syslog servers.

     It is assumed to not be meaningful to allow for user
     configuration of syslog to local files/programs/users on a
     network device.";

  revision 2021-10-13 {
    description
      "YANG 1.1 compatible.";
  }
  revision 2008-11-04 {
    description
      "draft-ietf-netmod-yang-02 compatible.";
  }
  revision 2007-08-29 {
    description
      "Syntax fixes after pyang validation.";
  }
  revision 2007-06-08 {
    description
      "Initial revision.";
  }

  typedef ncs_compliance_template_syslogLevel {
    type string;
  }

  typedef ncs_compliance_template_syslogFacility {
    type string;
  }

  typedef ncs_template_syslogLevel {
    type string;
  }

  typedef ncs_template_syslogFacility {
    type string;
  }

  typedef ncs_rpc_notif_syslogLevel {
    type enumeration {
      enum "emerg";
      enum "alert";
      enum "crit";
      enum "err";
      enum "warning";
      enum "notice";
      enum "info";
      enum "debug";
      enum "none";
      enum "all";
    }
  }

  typedef ncs_rpc_notif_syslogFacility {
    type enumeration {
      enum "auth";
      enum "authpriv";
      enum "cron";
      enum "daemon";
      enum "ftp";
      enum "kern";
      enum "lpr";
      enum "mail";
      enum "news";
      enum "security";
      enum "syslog" {
        tailf:code-name "sf_syslog";
      }
      enum "user";
      enum "uucp";
      enum "local0";
      enum "local1";
      enum "local2";
      enum "local3";
      enum "local4";
      enum "local5";
      enum "local6";
      enum "local7";
      enum "all" {
        tailf:code-name "sf_all";
      }
    }
  }

  typedef live_ncs_syslogLevel {
    type enumeration {
      enum "emerg";
      enum "alert";
      enum "crit";
      enum "err";
      enum "warning";
      enum "notice";
      enum "info";
      enum "debug";
      enum "none";
      enum "all";
    }
  }

  typedef live_ncs_syslogFacility {
    type enumeration {
      enum "auth";
      enum "authpriv";
      enum "cron";
      enum "daemon";
      enum "ftp";
      enum "kern";
      enum "lpr";
      enum "mail";
      enum "news";
      enum "security";
      enum "syslog" {
        tailf:code-name "sf_syslog";
      }
      enum "user";
      enum "uucp";
      enum "local0";
      enum "local1";
      enum "local2";
      enum "local3";
      enum "local4";
      enum "local5";
      enum "local6";
      enum "local7";
      enum "all" {
        tailf:code-name "sf_all";
      }
    }
  }

  typedef syslogLevel {
    type enumeration {
      enum "emerg";
      enum "alert";
      enum "crit";
      enum "err";
      enum "warning";
      enum "notice";
      enum "info";
      enum "debug";
      enum "none";
      enum "all";
    }
  }

  typedef syslogFacility {
    type enumeration {
      enum "auth";
      enum "authpriv";
      enum "cron";
      enum "daemon";
      enum "ftp";
      enum "kern";
      enum "lpr";
      enum "mail";
      enum "news";
      enum "security";
      enum "syslog" {
        tailf:code-name "sf_syslog";
      }
      enum "user";
      enum "uucp";
      enum "local0";
      enum "local1";
      enum "local2";
      enum "local3";
      enum "local4";
      enum "local5";
      enum "local6";
      enum "local7";
      enum "all" {
        tailf:code-name "sf_all";
      }
    }
  }

  grouping ncs_compliance_template_syslog {
    list server {
      // NCS patched for predictable order
      ordered-by user;
      key "name";
      leaf name {
        type string;
      }
      leaf enabled {
        type string;
      }
      list selector {
        // NCS patched for predictable order
        ordered-by user;
        key "name";
        leaf name {
          type string;
        }
        leaf negate {
          type string;
        }
        leaf comparison {
          type string;
        }
        leaf level {
          type ncs_compliance_template_syslogLevel;
        }
        leaf-list facility {
          // NCS patched for predictable order
          ordered-by user;
          type ncs_compliance_template_syslogFacility;
          // NCS drop min-elements statement
          // NCS drop max-elements statement
        }
      }
      leaf administrator {
        type string;
        tailf:hidden "maint";
      }
    }
  }

  grouping ncs_template_syslog {
    list server {
      // NCS patched for predictable order
      ordered-by user;
      key "name";
      leaf name {
        type string;
      }
      leaf enabled {
        type string;
      }
      list selector {
        // NCS patched for predictable order
        ordered-by user;
        key "name";
        leaf name {
          type string;
        }
        leaf negate {
          type string;
        }
        leaf comparison {
          type string;
        }
        leaf level {
          type ncs_template_syslogLevel;
        }
        leaf-list facility {
          // NCS patched for predictable order
          ordered-by user;
          type ncs_template_syslogFacility;
          // NCS drop min-elements statement
          // NCS drop max-elements statement
        }
      }
      leaf administrator {
        type string;
        tailf:hidden "maint";
      }
    }
  }

  grouping ncs_rpc_notif_syslog {
    list server {
      key "name";
      leaf name {
        type inet:host;
      }
      leaf enabled {
        type boolean;
      }
      list selector {
        key "name";
        leaf name {
          type int32;
        }
        leaf negate {
          type boolean;
        }
        leaf comparison {
          type enumeration {
            enum "same-or-higher";
            enum "same";
          }
        }
        leaf level {
          type ncs_rpc_notif_syslogLevel;
        }
        leaf-list facility {
          type ncs_rpc_notif_syslogFacility;
          min-elements 1;
          max-elements 8;
        }
      }
      leaf administrator {
        type string;
        tailf:hidden "maint";
      }
    }
  }

  grouping live_ncs_syslog {
    list server {
      key "name";
      leaf name {
        type inet:host;
      }
      leaf enabled {
        type boolean;
      }
      list selector {
        key "name";
        leaf name {
          type int32;
        }
        leaf negate {
          type boolean;
        }
        leaf comparison {
          type enumeration {
            enum "same-or-higher";
            enum "same";
          }
        }
        leaf level {
          type live_ncs_syslogLevel;
        }
        leaf-list facility {
          type live_ncs_syslogFacility;
          // NCS drop min-elements statement
          // NCS drop max-elements statement
        }
      }
      leaf administrator {
        type string;
        tailf:hidden "maint";
      }
      action archive-log {
        tailf:actionpoint ncsproxy {
          tailf:internal;
        }
        input {
          leaf archive-path {
            type string;
          }
          leaf compress {
            type boolean;
          }
        }
        output {
          leaf result {
            type string;
          }
        }
        // NCS drop tailf:exec
      }
    }
  }

  grouping syslog {
    list server {
      key "name";
      leaf name {
        type inet:host;
      }
      leaf enabled {
        type boolean;
      }
      list selector {
        key "name";
        leaf name {
          type int32;
        }
        leaf negate {
          type boolean;
        }
        leaf comparison {
          type enumeration {
            enum "same-or-higher";
            enum "same";
          }
        }
        leaf level {
          type syslogLevel;
        }
        leaf-list facility {
          type syslogFacility;
          min-elements 1;
          max-elements 8;
        }
      }
      leaf administrator {
        type string;
        tailf:hidden "maint";
      }
      action archive-log {
        tailf:actionpoint ncsproxy {
          tailf:internal;
        }
        input {
          leaf archive-path {
            type string;
          }
          leaf compress {
            type boolean;
          }
        }
        output {
          leaf result {
            type string;
          }
        }
        // NCS drop tailf:exec
      }
    }
  }
}
