module lb-nc-1.0 {
  yang-version 1.1;
  namespace "http://tail-f.com/ns/ned-id/lb-nc-1.0";
  prefix lb-nc-1.0;

  import lb-nc {
    prefix family;
  }

  identity lb-nc-1.0 {
    base family:lb-nc;
  }
}
