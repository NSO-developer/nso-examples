module router-cli {
  yang-version 1.1;
  namespace "http://tail-f.com/ns/ned-id/router-cli";
  prefix router-cli;

  import tailf-common {
    prefix tailf;
  }

  import tailf-ncs-ned {
    prefix ned;
  }

  identity router-cli {
    tailf:abstract;
    base ned:cli-ned-id;
  }
}
