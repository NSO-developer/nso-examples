submodule router-interfaces {
  // Generated by yanger -t ncs
  tailf:mount-id "router-cli-1.0:router-cli-1.0";

  yang-version 1.1;
  belongs-to router {
    prefix r;
  }

  import ietf-yang-types {
    prefix yang;
  }
  import ietf-inet-types {
    prefix inet;
  }
  include router-types;
  import tailf-common {
    prefix tailf;
  }
  import tailf-ncs {
    prefix ncs;
  }

  description
    "The 'interfaces' component provides support for configuring network
     interfaces, both link-level (including VLAN-tagged interfaces)
     and IP addresses (IPv4 and IPv6).

     The data model is loosely based on (a subset of) Juniper's, in
     particular the sub-division of interfaces into numbered 'logical
     units' - this allows for grouping of IP addresses, as well as for
     configuring VLAN tagging without exposing the interface naming
     scheme used natively by Linux for this.";

  revision 2021-10-13 {
    description
      "YANG 1.1 compatible.All counters are now config false.";
  }
  revision 2008-11-04 {
    description
      "draft-ietf-netmod-yang-02 compatible.";
  }
  revision 2007-08-29 {
    description
      "Syntax fixes after pyang validation.";
  }
  revision 2007-06-08 {
    description
      "Initial revision.";
  }

  typedef ncs_compliance_template_interfaceSpeed {
    type string;
  }

  typedef ncs_compliance_template_interfaceDuplex {
    type string;
  }

  typedef ncs_template_interfaceSpeed {
    type string;
  }

  typedef ncs_template_interfaceDuplex {
    type string;
  }

  typedef ncs_rpc_notif_interfaceSpeed {
    type enumeration {
      enum "ten" {
        value 10;
      }
      enum "hundred" {
        value 100;
      }
      enum "thousand" {
        value 1000;
      }
    }
  }

  typedef ncs_rpc_notif_interfaceDuplex {
    type enumeration {
      enum "half";
      enum "full";
    }
  }

  typedef live_ncs_interfaceSpeed {
    type enumeration {
      enum "ten" {
        value 10;
      }
      enum "hundred" {
        value 100;
      }
      enum "thousand" {
        value 1000;
      }
    }
  }

  typedef live_ncs_interfaceDuplex {
    type enumeration {
      enum "half";
      enum "full";
    }
  }

  typedef interfaceSpeed {
    type enumeration {
      enum "ten" {
        value 10;
      }
      enum "hundred" {
        value 100;
      }
      enum "thousand" {
        value 1000;
      }
    }
  }

  typedef interfaceDuplex {
    type enumeration {
      enum "half";
      enum "full";
    }
  }

  grouping ncs_compliance_template_commonPacketsCounters {
    leaf bytes {
      type string;
    }
    leaf packets {
      type string;
    }
    leaf errors {
      type string;
    }
    leaf dropped {
      type string;
    }
  }

  grouping ncs_compliance_template_txPacketsCounters {
    uses ncs_compliance_template_commonPacketsCounters;
    leaf collisions {
      type string;
    }
  }

  grouping ncs_compliance_template_interfaces {
    list interface {
      // NCS patched for predictable order
      ordered-by user;
      key "name";
      leaf name {
        type ncs_compliance_template_interfaceName;
      }
      leaf description {
        type string;
      }
      leaf enabled {
        type empty;
      }
      leaf speed {
        type ncs_compliance_template_interfaceSpeed;
        description
          "not supported for all types of interfaces";
      }
      leaf duplex {
        type ncs_compliance_template_interfaceDuplex;
        description
          "not supported for all types of interfaces";
      }
      leaf mtu {
        type string;
      }
      leaf mac {
        type string;
      }
      // NCS drop config false container status
      list unit {
        // NCS patched for predictable order
        ordered-by user;
        key "name";
        leaf name {
          type ncs_compliance_template_interfaceLogicalUnit;
        }
        leaf enabled {
          type string;
        }
        leaf description {
          type string;
        }
        leaf vlan-id {
          type string;
        }
        leaf-list arp {
          // NCS patched for predictable order
          ordered-by user;
          type string;
        }
        // NCS drop config false container status
        container family {
          choice family {
            case c1 {
              container inet {
                list address {
                  // NCS patched for predictable order
                  ordered-by user;
                  key "name";
                  leaf name {
                    type string;
                  }
                  leaf prefix-length {
                    type ncs_compliance_template_prefixLengthIPv4;
                  }
                  leaf broadcast {
                    type string;
                  }
                }
              }
            }
            case c2 {
              container inet6 {
                list address {
                  // NCS patched for predictable order
                  ordered-by user;
                  key "name";
                  leaf name {
                    type string;
                  }
                  leaf prefix-length {
                    type ncs_compliance_template_prefixLengthIPv6;
                  }
                }
              }
            }
          }
        }
      }
    }
  }

  grouping ncs_template_commonPacketsCounters {
    leaf bytes {
      type string;
    }
    leaf packets {
      type string;
    }
    leaf errors {
      type string;
    }
    leaf dropped {
      type string;
    }
  }

  grouping ncs_template_txPacketsCounters {
    uses ncs_template_commonPacketsCounters;
    leaf collisions {
      type string;
    }
  }

  grouping ncs_template_interfaces {
    list interface {
      // NCS patched for predictable order
      ordered-by user;
      key "name";
      leaf name {
        type ncs_template_interfaceName;
      }
      leaf description {
        type string;
      }
      leaf enabled {
        type empty;
      }
      leaf speed {
        type ncs_template_interfaceSpeed;
        description
          "not supported for all types of interfaces";
      }
      leaf duplex {
        type ncs_template_interfaceDuplex;
        description
          "not supported for all types of interfaces";
      }
      leaf mtu {
        type string;
      }
      leaf mac {
        type string;
      }
      // NCS drop config false container status
      list unit {
        // NCS patched for predictable order
        ordered-by user;
        key "name";
        leaf name {
          type ncs_template_interfaceLogicalUnit;
        }
        leaf enabled {
          type string;
        }
        leaf description {
          type string;
        }
        leaf vlan-id {
          type string;
        }
        leaf-list arp {
          // NCS patched for predictable order
          ordered-by user;
          type string;
        }
        // NCS drop config false container status
        container family {
          choice family {
            case c1 {
              container inet {
                list address {
                  // NCS patched for predictable order
                  ordered-by user;
                  key "name";
                  leaf name {
                    type string;
                  }
                  leaf prefix-length {
                    type ncs_template_prefixLengthIPv4;
                  }
                  leaf broadcast {
                    type string;
                  }
                }
              }
            }
            case c2 {
              container inet6 {
                list address {
                  // NCS patched for predictable order
                  ordered-by user;
                  key "name";
                  leaf name {
                    type string;
                  }
                  leaf prefix-length {
                    type ncs_template_prefixLengthIPv6;
                  }
                }
              }
            }
          }
        }
      }
    }
  }

  grouping ncs_rpc_notif_commonPacketsCounters {
    leaf bytes {
      type yang:counter64;
    }
    leaf packets {
      type yang:counter64;
    }
    leaf errors {
      type yang:counter32;
    }
    leaf dropped {
      type yang:counter32;
    }
  }

  grouping ncs_rpc_notif_txPacketsCounters {
    uses ncs_rpc_notif_commonPacketsCounters;
    leaf collisions {
      type yang:counter32;
    }
  }

  grouping ncs_rpc_notif_interfaces {
    list interface {
      key "name";
      leaf name {
        type ncs_rpc_notif_interfaceName;
      }
      leaf description {
        type string;
      }
      leaf enabled {
        type empty;
      }
      leaf speed {
        type ncs_rpc_notif_interfaceSpeed;
        description
          "not supported for all types of interfaces";
      }
      leaf duplex {
        type ncs_rpc_notif_interfaceDuplex;
        description
          "not supported for all types of interfaces";
      }
      leaf mtu {
        type int16 {
          range "68..1500";
        }
      }
      leaf mac {
        type yang:mac-address;
      }
      container status {
        config false;
        leaf link {
          type enumeration {
            enum "up";
            enum "down";
          }
        }
        leaf speed {
          type ncs_rpc_notif_interfaceSpeed;
        }
        leaf duplex {
          type ncs_rpc_notif_interfaceDuplex;
        }
        leaf mtu {
          type int32;
        }
        leaf mac {
          type yang:mac-address;
        }
        container receive {
          uses ncs_rpc_notif_commonPacketsCounters;
        }
        container transmit {
          uses ncs_rpc_notif_txPacketsCounters;
        }
      }
      list unit {
        key "name";
        leaf name {
          type ncs_rpc_notif_interfaceLogicalUnit;
        }
        leaf enabled {
          type boolean;
        }
        leaf description {
          type string;
        }
        leaf vlan-id {
          type uint16;
        }
        leaf-list arp {
          type enumeration {
            enum "no-gratuitous-arp-reply";
            enum "no-gratuitous-arp-request";
          }
        }
        container status {
          config false;
          container receive {
            uses ncs_rpc_notif_commonPacketsCounters;
          }
          container transmit {
            uses ncs_rpc_notif_txPacketsCounters;
          }
        }
        container family {
          choice family {
            case c1 {
              container inet {
                list address {
                  key "name";
                  leaf name {
                    type inet:ipv4-address;
                  }
                  leaf prefix-length {
                    type ncs_rpc_notif_prefixLengthIPv4;
                  }
                  leaf broadcast {
                    type inet:ipv4-address;
                  }
                }
              }
            }
            case c2 {
              container inet6 {
                list address {
                  key "name";
                  leaf name {
                    type inet:ipv6-address;
                  }
                  leaf prefix-length {
                    type ncs_rpc_notif_prefixLengthIPv6;
                  }
                }
              }
            }
          }
        }
      }
    }
  }

  grouping live_ncs_commonPacketsCounters {
    leaf bytes {
      type yang:counter64;
    }
    leaf packets {
      type yang:counter64;
    }
    leaf errors {
      type yang:counter32;
    }
    leaf dropped {
      type yang:counter32;
    }
  }

  grouping live_ncs_txPacketsCounters {
    uses live_ncs_commonPacketsCounters;
    leaf collisions {
      type yang:counter32;
    }
  }

  grouping live_ncs_interfaces {
    list interface {
      key "name";
      leaf name {
        type live_ncs_interfaceName;
      }
      leaf description {
        type string;
      }
      leaf enabled {
        type empty;
      }
      leaf speed {
        type live_ncs_interfaceSpeed;
        description
          "not supported for all types of interfaces";
      }
      leaf duplex {
        type live_ncs_interfaceDuplex;
        description
          "not supported for all types of interfaces";
      }
      leaf mtu {
        type int16 {
          range "68..1500";
        }
      }
      leaf mac {
        type yang:mac-address;
      }
      container status {
        leaf link {
          type enumeration {
            enum "up";
            enum "down";
          }
        }
        leaf speed {
          type live_ncs_interfaceSpeed;
        }
        leaf duplex {
          type live_ncs_interfaceDuplex;
        }
        leaf mtu {
          type int32;
        }
        leaf mac {
          type yang:mac-address;
        }
        container receive {
          uses live_ncs_commonPacketsCounters;
        }
        container transmit {
          uses live_ncs_txPacketsCounters;
        }
      }
      list unit {
        key "name";
        leaf name {
          type live_ncs_interfaceLogicalUnit;
        }
        leaf enabled {
          type boolean;
        }
        leaf description {
          type string;
        }
        leaf vlan-id {
          type uint16;
        }
        leaf-list arp {
          type enumeration {
            enum "no-gratuitous-arp-reply";
            enum "no-gratuitous-arp-request";
          }
        }
        container status {
          container receive {
            uses live_ncs_commonPacketsCounters;
          }
          container transmit {
            uses live_ncs_txPacketsCounters;
          }
        }
        container family {
          choice family {
            case c1 {
              container inet {
                list address {
                  key "name";
                  leaf name {
                    type inet:ipv4-address;
                  }
                  leaf prefix-length {
                    type live_ncs_prefixLengthIPv4;
                  }
                  leaf broadcast {
                    type inet:ipv4-address;
                  }
                }
              }
            }
            case c2 {
              container inet6 {
                list address {
                  key "name";
                  leaf name {
                    type inet:ipv6-address;
                  }
                  leaf prefix-length {
                    type live_ncs_prefixLengthIPv6;
                  }
                }
              }
            }
          }
        }
      }
    }
  }

  grouping commonPacketsCounters {
    leaf bytes {
      type yang:counter64;
    }
    leaf packets {
      type yang:counter64;
    }
    leaf errors {
      type yang:counter32;
    }
    leaf dropped {
      type yang:counter32;
    }
  }

  grouping txPacketsCounters {
    uses commonPacketsCounters;
    leaf collisions {
      type yang:counter32;
    }
  }

  grouping interfaces {
    list interface {
      key "name";
      leaf name {
        type interfaceName;
      }
      leaf description {
        type string;
      }
      leaf enabled {
        type empty;
      }
      leaf speed {
        type interfaceSpeed;
        description
          "not supported for all types of interfaces";
      }
      leaf duplex {
        type interfaceDuplex;
        description
          "not supported for all types of interfaces";
      }
      leaf mtu {
        type int16 {
          range "68..1500";
        }
      }
      leaf mac {
        type yang:mac-address;
      }
      // NCS drop config false container status
      list unit {
        key "name";
        leaf name {
          type interfaceLogicalUnit;
        }
        leaf enabled {
          type boolean;
        }
        leaf description {
          type string;
        }
        leaf vlan-id {
          type uint16;
        }
        leaf-list arp {
          type enumeration {
            enum "no-gratuitous-arp-reply";
            enum "no-gratuitous-arp-request";
          }
        }
        // NCS drop config false container status
        container family {
          choice family {
            case c1 {
              container inet {
                list address {
                  key "name";
                  leaf name {
                    type inet:ipv4-address;
                  }
                  leaf prefix-length {
                    type prefixLengthIPv4;
                  }
                  leaf broadcast {
                    type inet:ipv4-address;
                  }
                }
              }
            }
            case c2 {
              container inet6 {
                list address {
                  key "name";
                  leaf name {
                    type inet:ipv6-address;
                  }
                  leaf prefix-length {
                    type prefixLengthIPv6;
                  }
                }
              }
            }
          }
        }
      }
    }
  }
}
