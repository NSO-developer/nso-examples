module router-config {
  // Generated by yanger -t ncs
  tailf:mount-id "router-cli-1.0:router-cli-1.0";
  tailf:ncs-device-type "cli-ned";

  yang-version 1.1;
  namespace "http://example.com/router-config";
  prefix sc;

  import router {
    prefix r;
  }
  import tailf-common {
    prefix tailf;
  }
  import tailf-ncs {
    prefix ncs;
  }

  augment "/ncs:compliance/ncs:template/ncs:ned-id/ncs:config/r:sys" {
    container router-config {
      leaf want-reverse {
        type string;
        // NCS drop default statement
      }
      leaf trans-id-mode {
        type string;
        // NCS drop default statement
      }
    }
  }
  augment "/ncs:devices/ncs:template/ncs:ned-id/ncs:config/r:sys" {
    container router-config {
      leaf want-reverse {
        type string;
        // NCS drop default statement
      }
      leaf trans-id-mode {
        type string;
        // NCS drop default statement
      }
    }
  }
  augment "/ncs:devices/ncs:device/ncs:live-status/r:sys" {
    container router-config {
      tailf:ncs-device-type "cli-ned";
      tailf:display-when "not(../../../ncs:module) or ../../../ncs:module[ncs:name='router-config'] or (../../../ncs:live-status-protocol[not(ncs:capability)]) or (../../../ncs:live-status-protocol/ncs:capability/ncs:module[.='router-config'])";
      leaf want-reverse {
        type boolean;
        // NCS drop default statement
      }
      leaf trans-id-mode {
        type enumeration {
          enum "unique_string";
          enum "none";
        }
        // NCS drop default statement
      }
    }
  }
  augment "/ncs:devices/ncs:device/ncs:config/r:sys" {
    container router-config {
      tailf:ncs-device-type "cli-ned";
      tailf:display-when "not(../../../ncs:module) or ../../../ncs:module[ncs:name='router-config']";
      leaf want-reverse {
        type boolean;
        default "false";
      }
      leaf trans-id-mode {
        type enumeration {
          enum "unique_string";
          enum "none";
        }
        default "unique_string";
      }
    }
  }
}
